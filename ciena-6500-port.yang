module ciena-6500-port {
  namespace "urn:ciena:params:xml:ns:yang:ciena-6500-port";
  prefix port;

  import ciena-6500-enums {
    prefix ciena-6500-enums;
  }
  import ciena-6500-types {
    prefix ciena-6500-types;
  }
  import ciena-common-yang {
    prefix yang;
  }

  organization
    "Ciena Corporation";
  contact
    "Web URL: http://www.ciena.com";
  description
    "This modules describes Ciena's port object for the 6500 platform";

  revision 2023-10-18 {
    description
      "6500 Release 15.60 OA
         container port
           list ptp
           - Added leaf: los-thr
           list ettp
           - Added leaf: time-slot-assignment
         rpc port-show-ptp
           output
             list output
             - Added leaf: los-thr
         rpc port-show-ettp
           output
             list output
             - Added leaf: time-slot-assignment";
  }
  revision 2023-06-23 {
    description
      "6500 Release 15.50 SC
       - Added rpc: port-show-pdh
       - Added rpc: port-enable-pdh
       - Added rpc: port-disable-pdh
       - Added rpc: port-operate-loopback-pdh
       - Added rpc: port-release-loopback-pdh
       - Added rpc: port-show-loopback-pdh
       - Added rpc: port-alw-loopback-pdh
       - Added rpc: port-inh-loopback-pdh
       - Added rpc: port-show-path
       - Added rpc: port-enable-path
       - Added rpc: port-disable-path
       - Added rpc: port-operate-loopback-path
       - Added rpc: port-release-loopback-path
       - Added rpc: port-show-loopback-path
       - Added rpc: port-show-pktiwf
       - Added rpc: port-enable-pktiwf
       - Added rpc: port-disable-pktiwf
         rpc port-show-ptp
           output
             list output
             - Added leaf: line-build-out
             - Added leaf: line-cde
               leaf rx-mon
               - Changed type from ciena-6500-enums:BOOL_YES_NO_defaultNO to enumeration
                 type enumeration
                 - Added enum: YES
                 - Added enum: NO
               leaf rx-term
               - Changed type from ciena-6500-enums:BOOL_YES_NO_defaultNO to enumeration
                 type enumeration
                 - Added enum: YES
                 - Added enum: NO
         rpc port-show-otuttp
           output
             list output
             - Added leaf: ts-profile
             - Added leaf: osrp-line-mode
         rpc port-show-sttp
           output
             list output
             - Added leaf: stformat
             - Added leaf: tx-trc
             - Added leaf: rx-trc
             - Added leaf: stfmode
             - Added leaf: uneqmode
             - Added leaf: timing-reference
         rpc port-show-oductp
           output
             list output
             - Added leaf: num-flexts
         container port
         - Added list: pdh
         - Added list: path
         - Added list: pktiwf
           container loopback
           - Added list: pdh
           - Added list: path
           list ptp
           - Added leaf: line-build-out
           - Added leaf: line-cde
             leaf rx-mon
             - Changed type from ciena-6500-enums:BOOL_YES_NO_defaultNO to enumeration
               type enumeration
               - Added enum: YES
               - Added enum: NO
             leaf rx-term
             - Changed type from ciena-6500-enums:BOOL_YES_NO_defaultNO to enumeration
               type enumeration
               - Added enum: YES
               - Added enum: NO
           list otuttp
           - Added leaf: ts-profile
           - Added leaf: osrp-line-mode
             leaf osrp-channel
             - Changed config from false to true
           list sttp
           - Added leaf: stformat
           - Added leaf: stfmode
           - Added leaf: tx-trc
           - Added leaf: rx-trc
           - Added leaf: uneqmode
           - Added leaf: timing-reference
           - Added leaf: expstrc
           - Added leaf: txstrc
             leaf-list sst
             - Changed config from false to true
             - Changed type from ciena-6500-enums:SSTfac to enumeration
               type enumeration
               - Added enum: AINS
               - Added enum: AINS-DEA
               - Added enum: BRIDGED
               - Added enum: SWITCHED
               - Added enum: ROLL
               - Added enum: ACT
               - Added enum: IDLE
               - Added enum: STBYS
               - Added enum: WRK
               - Added enum: ERRANL
               - Added enum: PSI
               - Added enum: FLT
               - Added enum: MEA
               - Added enum: TSTF
               - Added enum: UEQ
               - Added enum: SGEO
               - Added enum: DISCD
               - Added enum: LPBK
               - Added enum: TS
               - Added enum: FAF
               - Added enum: STBYH
               - Added enum: WRKRX
               - Added enum: WRKTX
               - Added enum: PRTCL
               - Added enum: UAS
               - Added enum: NOSITE
               - Added enum: NOAM
               - Added enum: MON
               - Added enum: MSC
               - Added enum: PROTECTED
               - Added enum: MT
               - Added enum: DSBLD
               - Added enum: INHIP
               - Added enum: L2DSBLD
               - Added enum: TSGEN
               - Added enum: TSMON
               - Added enum: TSRECIRC
               - Added enum: TSTIP
               - Added enum: TSTCOMPLD
               - Added enum: TS-DEA
           list oduttp
             leaf flex-type
             - Changed config from false to true
           list oductp
           - Added leaf: num-flexts";
  }
  revision 2022-10-27 {
    description
      "6500 Release 12.85 PR
         rpc port-show-flex
           output
             list output
               leaf hold-off
                 type ciena-6500-types:INT
                 - Changed range from 0 | 100 | 200 | 300 | 400 | 500 | 600 | 700 | 800 | 900 | 1000 to 0 | 100 | 200..2000
         rpc port-show-otm
           output
             list output
             - Added leaf: optical-sf-rept
             - Added leaf: mate-info
         rpc port-show-ptp
           output
             list output
             - Added leaf: optical-sf-rept
               leaf fec-frmt
               - Changed type from enumeration to ciena-6500-enums:PTP_FECFrmt
         rpc port-operate-loopback-otuttp
           input
           - Added leaf: loopback-qual
         rpc port-operate-loopback-ettp
           input
           - Added leaf: loopback-qual
         rpc port-show-oduttp
           output
             list output
             - Added leaf: gcc1-mode
             - Added leaf: gcc2-mode
         container port
           list flex
             leaf tx-con
               type enumeration
               - Added enum: AISL
             leaf hold-off
               type ciena-6500-types:INT
               - Changed range from 0 | 100 | 200 | 300 | 400 | 500 | 600 | 700 | 800 | 900 | 1000 to 0 | 100 | 200..2000
           list otm
           - Added leaf: optical-sf-rept
           - Added leaf: mate-info
           list ptp
           - Added leaf: optical-sf-rept
             leaf fec-frmt
             - Changed type from enumeration to ciena-6500-enums:PTP_FECFrmt
             leaf-list sst
               type enumeration
               - Added enum: TSTIP
               - Added enum: TSTCOMPLD
           list otuttp
             leaf-list sst
               type enumeration
               - Added enum: TSTIP
               - Added enum: TSTCOMPLD
           list ettp
             leaf-list sst
               type enumeration
               - Added enum: TSTIP
               - Added enum: TSTCOMPLD
           list oduttp
           - Added leaf: gcc1-mode
           - Added leaf: gcc2-mode
           list tcm
             leaf-list sst
               type enumeration
               - Added enum: TSTIP
               - Added enum: TSTCOMPLD
           list flexi
             leaf-list sst
               type enumeration
               - Added enum: TSTIP
               - Added enum: TSTCOMPLD";
  }
  revision 2021-07-08 {
    description
      "6500 Release 12.80 BP
       - Added rpc: port-show-msi-oduttp
         rpc port-show-eth10g
           output
             list output
             - Added leaf: lldpmon
         rpc port-show-ethn
           output
             list output
             - Added leaf: lldpmon
         rpc port-show-ptp
           output
             list output
             - Added leaf: hold-off
             - Added leaf: ccda-thr
             - Added leaf: said
         rpc port-show-otuttp
           output
             list output
               leaf num-ts
                 type ciena-6500-types:INT
                 - Changed range from 1..160 to 1..320
               leaf act-num-ts
                 type ciena-6500-types:INT
                 - Changed range from 20..160 to 20..320
         rpc port-show-ettp
           output
             list output
             - Added leaf: lldpmon
         rpc port-show-oduttp
           output
             list output
               leaf trib-slot-assignment
                 type string
                 - Changed length from 1..50 to 1..99
               leaf num-ts
                 type ciena-6500-types:INT
                 - Changed range from 1..160 to 1..320
               leaf rx-ts
                 type string
                 - Changed length from 1..24 to 1..99
               leaf ex-rx-ts
                 type string
                 - Changed length from 1..24 to 1..99
               leaf prov-msi
                 type string
                 - Changed length from 1..800 to 1..1600
               leaf rx-msi
                 type string
                 - Changed length from 1..800 to 1..1600
               leaf act-avail-ts
                 type string
                 - Changed length from 1..160 to 1..320
         rpc port-show-oductp
           output
             list output
             - Added leaf-list: caid
               leaf trib-slot-assignment
                 type string
                 - Changed length from 1..50 to 1..99
               leaf num-ts
                 type ciena-6500-types:INT
                 - Changed range from 1..80 to 1..320
               leaf rx-ts
                 type string
                 - Changed length from 1..24 to 1..99
               leaf ex-rx-ts
                 type string
                 - Changed length from 1..24 to 1..99
               leaf act-avail-ts
                 type string
                 - Changed length from 1..160 to 1..320
         rpc port-disable-tcm
           input
             leaf sst
             - Added mandatory: true 
         container port
         - Added list: msi-oduttp
           list eth10g
           - Added leaf: lldpmon
           list ethn
           - Added leaf: lldpmon
           list ptp
           - Added leaf: hold-off
           - Added leaf: ccda-thr
           - Added leaf: said
             leaf-list sst
               type enumeration
               - Added enum: TS-DEA
           list otuttp
             leaf num-ts
               type ciena-6500-types:INT
               - Changed range from 1..160 to 1..320
             leaf-list sst
               type enumeration
               - Added enum: TS-DEA
             leaf act-num-ts
               type ciena-6500-types:INT
               - Changed range from 20..160 to 20..320
           list ettp
           - Added leaf: lldpmon
             leaf-list sst
               type enumeration
               - Added enum: TS-DEA
           list oduttp
             leaf trib-slot-assignment
               type string
               - Changed length from 1..50 to 1..99
             leaf num-ts
               type ciena-6500-types:INT
               - Changed range from 1..160 to 1..320
             leaf rx-ts
               type string
               - Changed length from 1..24 to 1..99
             leaf ex-rx-ts
               type string
               - Changed length from 1..24 to 1..99
             leaf prov-msi
               type string
               - Changed length from 1..800 to 1..1600
             leaf rx-msi
               type string
               - Changed length from 1..800 to 1..1600
             leaf act-avail-ts
               type string
               - Changed length from 1..160 to 1..320
           list oductp
           - Added leaf-list: caid
             leaf trib-slot-assignment
               type string
               - Changed length from 1..50 to 1..99
             leaf num-ts
               type ciena-6500-types:INT
               - Changed range from 1..80 to 1..320
             leaf rx-ts
               type string
               - Changed length from 1..24 to 1..99
             leaf ex-rx-ts
               type string
               - Changed length from 1..24 to 1..99
             leaf act-avail-ts
               type string
               - Changed length from 1..160 to 1..320
           list tcm
             leaf-list sst
               type enumeration
               - Added enum: TS-DEA
           list flexi
             leaf-list sst
               type enumeration
               - Added enum: TS-DEA";
  }
  revision 2020-09-25 {
    description
      "6500 Release 12.72 XQ
       - Removed rpc: port-disable-eth
       - Removed rpc: port-disable-eth100
       - Removed rpc: port-enable-eth
       - Removed rpc: port-enable-eth100
       - Removed rpc: port-disable-lag
       - Removed rpc: port-enable-lag
       - Removed rpc: port-delete-lag-port
       - Removed rpc: port-enable-fiber-channel
       - Removed rpc: port-disable-fiber-channel
       - Removed rpc: port-disable-oc3
       - Removed rpc: port-enable-oc3
       - Removed rpc: port-disable-oc12
       - Removed rpc: port-enable-oc12
       - Removed rpc: port-disable-oc48
       - Removed rpc: port-enable-oc48
       - Removed rpc: port-init-dispscan-otm2
       - Removed rpc: port-measure-rawber-otm2
       - Removed rpc: port-show-trace-flex
       - Added rpc: port-show-otminfo
       - Added rpc: port-show-loopback-otuttp
       - Added rpc: port-show-fttp
       - Added rpc: port-show-loopback-sttp
       - Added rpc: port-show-loopback-ettp
       - Added rpc: port-show-loopback-oduttp
       - Added rpc: port-show-loopback-oductp
       - Added rpc: port-show-loopback-cbrttp
       - Added rpc: port-disable-flexi
       - Added rpc: port-enable-flexi
       - Added rpc: port-show-flexi
       - Added rpc: port-show-pc
       - Added rpc: port-show-wavelength-rules
       - Added rpc: port-show-vcp
         rpc port-show-wan
           output
             list output
             - Removed key
               leaf-list sst
                 type enumeration
                 - Added enum: AINS-DEA
         rpc port-show-eth10g
           output
             list output
             - Removed key
         rpc port-show-ethn
           output
             list output
             - Removed key
         rpc port-show-flex
           output
             list output
             - Removed key
         rpc port-show-oc3
           output
             list output
             - Removed key
         rpc port-show-oc12
           output
             list output
             - Removed key
         rpc port-show-oc48
           output
             list output
             - Removed key
         rpc port-show-oc192
           output
             list output
             - Removed key
               leaf-list sst
                 type enumeration
                 - Added enum: TSGEN
                 - Added enum: TSMON
         rpc port-show-oc768
           output
             list output
             - Removed key
               leaf-list sst
                 type enumeration
                 - Added enum: DISCD
                 - Added enum: TSGEN
                 - Added enum: TSMON
         rpc port-show-otm2
           output
             list output
             - Removed key
               leaf tx-fec-frmt
                 type enumeration
                 - Added enum: QFEC
                 - Added enum: EFEC
                 - Added enum: LDPCFEC
               leaf-list sst
                 type enumeration
                 - Added enum: WRKRX
                 - Added enum: WRKTX
                 - Added enum: STBYH
                 - Added enum: PSI
         rpc port-show-otm3
           output
             list output
             - Removed key
               leaf-list sst
                 type enumeration
                 - Added enum: WRKRX
                 - Added enum: WRKTX
                 - Added enum: STBYH
                 - Added enum: PSI
         rpc port-show-otm
           output
             list output
             - Removed key
               leaf-list sst
                 type enumeration
                 - Added enum: WRKRX
                 - Added enum: WRKTX
                 - Added enum: STBYH
                 - Added enum: PSI
         rpc port-show-sts192c
           output
             list output
             - Removed key
         rpc port-show-tti-odu
           output
             list output
             - Removed key
         rpc port-show-ptp
           input
           - Added leaf: stat-data
           output
             list output
             - Removed key
             - Added leaf: ser-path-disp-min-prov
             - Added leaf: ser-path-disp-max-prov
             - Added leaf: mate-info
             - Added leaf: laser-status
             - Added leaf: lqs-managed
             - Added leaf: rqst-lqs-managed
             - Added leaf: laser-tuned
             - Added leaf: custom-key
               leaf rx-fec-frmt
                 type enumeration
                 - Added enum: RS10_KP4
                 - Added enum: TFEC
               leaf tx-fec-frmt
                 type enumeration
                 - Added enum: RS10_KP4
                 - Added enum: TFEC
               leaf fec-frmt
                 type enumeration
                 - Added enum: RS10_KP4
                 - Added enum: TFEC
         rpc port-show-otuttp
           output
             list output
             - Removed key
               leaf otu-oh-non-term
                 type enumeration
                 - Added enum: GCC0MODE1
         rpc port-show-sttp
           output
             list output
             - Removed key
         rpc port-show-ettp
           output
             list output
             - Removed key
         rpc port-show-oduttp
           output
             list output
             - Removed key
               leaf trib-slot-assignment
                 type string
                 - Changed length from 1..24 to 1..50
         rpc port-show-oductp
           output
             list output
             - Removed key
               leaf trib-slot-assignment
                 type string
                 - Changed length from 1..51 to 1..50
         rpc port-show-tcm
           output
             list output
             - Removed key
             - Added leaf: tcm-txcondtype
         rpc port-show-cbrttp
           output
             list output
             - Removed key
         rpc port-show-odu
           output
             list output
             - Removed key
         rpc port-show-facgrp
           output
             list output
             - Removed key
         rpc port-show-facgrpmbr
           output
             list output
             - Removed key
         container port
         - Removed container: trace
         - Removed list: eth
         - Removed list: eth100
         - Removed list: lag
         - Removed list: lag-port
         - Removed list: fiber-channel
         - Added list: flexi
           list wan
             leaf-list sst
               type enumeration
               - Added enum: AINS-DEA
           list oc192
             leaf-list sst
               type enumeration
               - Added enum: TSGEN
               - Added enum: TSMON
           list oc768
             leaf-list sst
               type enumeration
               - Added enum: DISCD
               - Added enum: TSGEN
               - Added enum: TSMON
           list otm2
             leaf tx-fec-frmt
               type enumeration
               - Added enum: QFEC
               - Added enum: EFEC
               - Added enum: LDPCFEC
             leaf-list sst
               type enumeration
               - Added enum: WRKRX
               - Added enum: WRKTX
               - Added enum: STBYH
               - Added enum: PSI
           list otm3
             leaf-list sst
               type enumeration
               - Added enum: WRKRX
               - Added enum: WRKTX
               - Added enum: STBYH
               - Added enum: PSI
           list otm
             leaf-list sst
               type enumeration
               - Added enum: WRKRX
               - Added enum: WRKTX
               - Added enum: STBYH
               - Added enum: PSI
           list sts192c
           - Changed config from true to false
           - Removed leaf: mon
           - Removed leaf: exptrc
           - Removed leaf: trc
             leaf expsglbl
             - Changed config from true to false
             leaf sglbl
             - Changed config from true to false
             leaf trcformat
             - Changed config from true to false
             leaf prime
             - Changed config from true to false
           list ptp
           - Added leaf: ser-path-disp-min-prov
           - Added leaf: ser-path-disp-max-prov
           - Added leaf: laser-status
           - Added leaf: lqs-managed
           - Added leaf: custom-key
           - Added leaf: mate-info
           - Added leaf: rqst-lqs-managed
           - Added leaf: laser-tuned
             leaf fec-frmt
               type enumeration
               - Added enum: RS10_KP4
               - Added enum: TFEC
             leaf rx-fec-frmt
               type enumeration
               - Added enum: RS10_KP4
               - Added enum: TFEC
             leaf tx-fec-frmt
               type enumeration
               - Added enum: RS10_KP4
               - Added enum: TFEC
           list otuttp
             leaf otu-oh-non-term
               type enumeration
               - Added enum: GCC0MODE1
             leaf supported-term-pt
             - Changed config from false to true
           list oduttp
             leaf trib-slot-assignment
               type string
               - Changed length from 1..24 to 1..50
             leaf ex-pt
             - Changed config from false to true
           list oductp
             leaf trib-slot-assignment
               type string
               - Changed length from 1..51 to 1..50
           list tcm
           - Added leaf: tcm-txcondtype";
  }
  revision 2019-10-17 {
    description
      "6500 Release 12.60 JK
         rpc port-show-wan
           output
             list output
             - Added key: wan 
             - Added leaf: rxmon
             - Added leaf: rxterm
             - Added leaf: tx-mon
             - Added leaf: tx-term
         rpc port-show-eth10g
           output
             list output
             - Added key: eth10g 
         rpc port-show-ethn
           output
             list output
             - Added key: ethn 
         rpc port-show-flex
           output
             list output
             - Added key: flex 
               leaf tx-con
                 type enumeration
                 - Added enum: LNKFLTC1C2
         rpc port-show-oc3
           output
             list output
             - Added key: oc3 
         rpc port-show-oc12
           output
             list output
             - Added key: oc12 
         rpc port-show-oc48
           output
             list output
             - Added key: oc48 
             - Removed leaf: rx-act-power
             - Removed leaf: tx-act-power
             - Removed leaf: rx-min-power
             - Removed leaf: rx-max-power
             - Removed leaf: tx-min-power
             - Removed leaf: tx-max-power
             - Added leaf: och-rx-act-power
             - Added leaf: och-tx-act-power
             - Added leaf: och-rx-min-power
             - Added leaf: och-rx-max-power
             - Added leaf: och-tx-min-power
             - Added leaf: och-tx-max-power
         rpc port-show-oc192
           output
             list output
             - Added key: oc192 
             - Removed leaf: rx-act-power
             - Removed leaf: rx-min-power
             - Removed leaf: rx-max-power
             - Removed leaf: tx-act-power
             - Removed leaf: tx-min-power
             - Removed leaf: tx-max-power
             - Removed leaf: tx-wvlngth-prov
             - Removed leaf: tx-wvlngth-min
             - Removed leaf: tx-wvlngth-max
             - Removed leaf: tx-wvlngth-spacing
             - Removed leaf: laser-off-far-end-fail
             - Added leaf: och-rx-act-power
             - Added leaf: och-rx-min-power
             - Added leaf: och-rx-max-power
             - Added leaf: och-tx-act-power
             - Added leaf: och-tx-min-power
             - Added leaf: och-tx-max-power
             - Added leaf: ochtxwvlngthprov
             - Added leaf: ochtxwvlngthmin
             - Added leaf: ochtxwvlngthmax
             - Added leaf: ochtxwvlngthspacing
             - Added leaf: laserofffarendfail
               leaf-list sst
                 type enumeration
                 - Removed enum: TSGEN
                 - Removed enum: TSMON
         rpc port-show-oc768
           output
             list output
             - Added key: oc768 
             - Removed leaf: rx-act-power
             - Removed leaf: rx-min-power
             - Removed leaf: rx-max-power
             - Removed leaf: tx-act-power
             - Removed leaf: tx-min-power
             - Removed leaf: tx-max-power
             - Removed leaf: laser-off-far-end-fail
             - Added leaf: och-rx-act-power
             - Added leaf: och-rx-min-power
             - Added leaf: och-rx-max-power
             - Added leaf: och-tx-act-power
             - Added leaf: och-tx-min-power
             - Added leaf: och-tx-max-power
             - Added leaf: laserofffarendfail
               leaf-list sst
                 type enumeration
                 - Removed enum: TSGEN
                 - Removed enum: TSMON
         rpc port-show-otm2
           output
             list output
             - Added key: otm2aid 
         rpc port-measure-rawber-otm2
           output
             list output
             - Added key: otm2aid 
         rpc port-show-otm3
           output
             list output
             - Added key: otm3aid 
         rpc port-show-otm
           output
             list output
             - Added key: otmaid 
               leaf laser-freq-thr
                 type decimal64
                 - Changed range from 0..3.0 to 0.0..3.0
         rpc port-show-sts192c
           output
             list output
             - Added key: sts192c 
         rpc port-show-tti-odu
           output
             list output
             - Added key: odun 
         rpc port-show-trace-flex
           output
             list output
             - Added key: flex 
         rpc port-show-ptp
           output
             list output
             - Added key: ptp 
             - Added leaf: reach-type
             - Added leaf: line-fail
             - Added leaf: rx-mon
             - Added leaf: rx-term
               leaf rx-fec-frmt
                 type enumeration
                 - Added enum: EFEC
                 - Added enum: LDPCFEC
               leaf tx-fec-frmt
                 type enumeration
                 - Added enum: EFEC
                 - Added enum: LDPCFEC
               leaf cond-type
               - Changed type from enumeration to ciena-6500-enums:ptpCondType
               leaf fec-frmt
                 type enumeration
                 - Added enum: EFEC
                 - Added enum: LDPCFEC
               leaf pre-fec-sf-th-lev
               - Changed default from 0.0 to 0.00
               leaf pre-fec-sd-th-lev
               - Changed default from 0.5 to 0.50
               leaf laser-freq-thr
                 type decimal64
                 - Changed range from 0..3.0 to 0.0..3.0
         rpc port-show-otuttp
           output
             list output
             - Added key: otu 
             - Added leaf: oper-chg-evt
             - Added leaf: sapi-chg-evt
             - Added leaf: dapi-chg-evt
             - Added leaf: rx-mon
             - Added leaf: rx-term
             - Added leaf: tx-mon
             - Added leaf: tx-term
             - Added leaf: degm-intv
             - Added leaf: degthr-percentage
         rpc port-disable-otuttp
           input
           - Added leaf: sst
         rpc port-show-sttp
           output
             list output
             - Added key: sttp 
             - Added leaf: rxmon
             - Added leaf: rxterm
             - Added leaf: tx-mon
             - Added leaf: tx-term
             - Added leaf: hold-off
         rpc port-disable-sttp
           input
           - Added leaf: sst
         rpc port-show-ettp
           output
             list output
             - Added key: ettp 
             - Added leaf: rx-mon
             - Added leaf: rx-term
             - Added leaf: tx-mon
             - Added leaf: tx-term
               leaf fec-frmt
                 type enumeration
                 - Added enum: RS10_KP4
         rpc port-show-oduttp
           output
             list output
             - Added key: oduttp 
             - Added leaf: rxmon
             - Added leaf: rxterm
             - Added leaf: tx-mon
             - Added leaf: tx-term
             - Added leaf: degm-intv
             - Added leaf: degthr-percentage
         rpc port-show-oductp
           output
             list output
             - Added key: oductp 
             - Added leaf: rx-mon
             - Added leaf: rx-term
             - Added leaf: tx-mon
             - Added leaf: tx-term
             - Added leaf: degm-intv
             - Added leaf: degthr-percentage
             - Added leaf-list: oductp-rxcondtrig
         rpc port-show-tcm
           output
             list output
             - Added key: tcm 
             - Added leaf: rx-mon
             - Added leaf: rx-term
             - Added leaf: tx-mon
             - Added leaf: tx-term
             - Added leaf: degm-intv
             - Added leaf: degthr-percentage
             - Added leaf: tcm-condtype
             - Added leaf: rxcondhold-off
             - Added leaf-list: tcm-rxcondtrig
             - Added leaf: tcm-ltcactmode
             - Added leaf: tcm-ltcalmmode
               leaf tcm-mode
               - Changed type from enumeration to ciena-6500-enums:tcmMode
         rpc port-show-cbrttp
           output
             list output
             - Added key: cbrttp 
               leaf pre-fec-sf-th-lev
               - Changed default from 0.0 to 0.00
               leaf pre-fec-sd-th-lev
               - Changed default from 0.5 to 0.50
         rpc port-show-odu
           output
             list output
             - Added key: odun 
         rpc port-show-facgrp
           output
             list output
             - Added key: facgrp 
         rpc port-show-facgrpmbr
           output
             list output
             - Added key: facgrpmbr 
         container port
           list wan
           - Added leaf: rxmon
           - Added leaf: rxterm
           - Added leaf: tx-mon
           - Added leaf: tx-term
             leaf if-type
             - Removed mandatory
             leaf fcs-err-frames
             - Added default: DISCARD 
           list flex
             leaf tx-con
               type enumeration
               - Added enum: LNKFLTC1C2
           list oc48
           - Removed leaf: rx-act-power
           - Removed leaf: tx-act-power
           - Removed leaf: rx-min-power
           - Removed leaf: rx-max-power
           - Removed leaf: tx-min-power
           - Removed leaf: tx-max-power
           - Removed leaf: laser-off-far-end-fail
           - Added leaf: och-rx-act-power
           - Added leaf: och-tx-act-power
           - Added leaf: och-rx-min-power
           - Added leaf: och-rx-max-power
           - Added leaf: och-tx-min-power
           - Added leaf: och-tx-max-power
           - Added leaf: laserofffarendfail
           list oc192
           - Removed leaf: laser-off-far-end-fail
           - Removed leaf: tx-wvlngth-prov
           - Removed leaf: rx-act-power
           - Removed leaf: rx-min-power
           - Removed leaf: rx-max-power
           - Removed leaf: tx-act-power
           - Removed leaf: tx-min-power
           - Removed leaf: tx-max-power
           - Removed leaf: tx-wvlngth-min
           - Removed leaf: tx-wvlngth-max
           - Removed leaf: tx-wvlngth-spacing
           - Added leaf: laserofffarendfail
           - Added leaf: ochtxwvlngthprov
           - Added leaf: och-rx-act-power
           - Added leaf: och-rx-min-power
           - Added leaf: och-rx-max-power
           - Added leaf: och-tx-act-power
           - Added leaf: och-tx-min-power
           - Added leaf: och-tx-max-power
           - Added leaf: ochtxwvlngthmin
           - Added leaf: ochtxwvlngthmax
           - Added leaf: ochtxwvlngthspacing
             leaf-list sst
               type enumeration
               - Removed enum: TSGEN
               - Removed enum: TSMON
           list oc768
           - Removed leaf: laser-off-far-end-fail
           - Removed leaf: rx-act-power
           - Removed leaf: rx-min-power
           - Removed leaf: rx-max-power
           - Removed leaf: tx-act-power
           - Removed leaf: tx-min-power
           - Removed leaf: tx-max-power
           - Added leaf: laserofffarendfail
           - Added leaf: och-rx-act-power
           - Added leaf: och-rx-min-power
           - Added leaf: och-rx-max-power
           - Added leaf: och-tx-act-power
           - Added leaf: och-tx-min-power
           - Added leaf: och-tx-max-power
             leaf-list sst
               type enumeration
               - Removed enum: TSGEN
               - Removed enum: TSMON
           list otm
             leaf laser-freq-thr
               type decimal64
               - Changed range from 0..3.0 to 0.0..3.0
           list ptp
           - Added leaf: reach-type
           - Added leaf: line-fail
           - Added leaf: rx-mon
           - Added leaf: rx-term
             leaf cond-type
             - Changed type from enumeration to ciena-6500-enums:ptpCondType
             leaf fec-frmt
               type enumeration
               - Added enum: EFEC
               - Added enum: LDPCFEC
             leaf pre-fec-sf-th-lev
             - Changed default from 0.0 to 0.00
             leaf pre-fec-sd-th-lev
             - Changed default from 0.5 to 0.50
             leaf laser-freq-thr
               type decimal64
               - Changed range from 0..3.0 to 0.0..3.0
             leaf rx-fec-frmt
               type enumeration
               - Added enum: EFEC
               - Added enum: LDPCFEC
             leaf tx-fec-frmt
               type enumeration
               - Added enum: EFEC
               - Added enum: LDPCFEC
           list otuttp
           - Added leaf: oper-chg-evt
           - Added leaf: sapi-chg-evt
           - Added leaf: dapi-chg-evt
           - Added leaf: degm-intv
           - Added leaf: degthr-percentage
           - Added leaf: rx-mon
           - Added leaf: rx-term
           - Added leaf: tx-mon
           - Added leaf: tx-term
           list sttp
           - Added leaf: hold-off
           - Added leaf: rxmon
           - Added leaf: rxterm
           - Added leaf: tx-mon
           - Added leaf: tx-term
           list ettp
           - Added leaf: rx-mon
           - Added leaf: rx-term
           - Added leaf: tx-mon
           - Added leaf: tx-term
             leaf mapping
             - Changed type from enumeration to ciena-6500-enums:EttpMapping
             leaf fec-frmt
               type enumeration
               - Added enum: RS10_KP4
           list oduttp
           - Added leaf: degm-intv
           - Added leaf: degthr-percentage
           - Added leaf: rxmon
           - Added leaf: rxterm
           - Added leaf: tx-mon
           - Added leaf: tx-term
           list oductp
           - Added leaf: degm-intv
           - Added leaf: degthr-percentage
           - Added leaf-list: oductp-rxcondtrig
           - Added leaf: rx-mon
           - Added leaf: rx-term
           - Added leaf: tx-mon
           - Added leaf: tx-term
           list tcm
           - Added leaf: degm-intv
           - Added leaf: degthr-percentage
           - Added leaf: tcm-condtype
           - Added leaf: rxcondhold-off
           - Added leaf-list: tcm-rxcondtrig
           - Added leaf: tcm-ltcactmode
           - Added leaf: tcm-ltcalmmode
           - Added leaf: rx-mon
           - Added leaf: rx-term
           - Added leaf: tx-mon
           - Added leaf: tx-term
             leaf tcm-mode
             - Changed type from enumeration to ciena-6500-enums:tcmMode
           list cbrttp
             leaf pre-fec-sf-th-lev
             - Changed default from 0.0 to 0.00
             leaf pre-fec-sd-th-lev
             - Changed default from 0.5 to 0.50";
  }
  revision 2019-01-16 {
    description
      "6500 Release 12.40 SS
       - Added rpc: port-show-facgrp
       - Added rpc: port-show-facgrpmbr
         rpc port-show-ethn
           output
             list output
             - Added leaf: mtu
         rpc port-show-otm
           output
             list output
             - Added leaf: exp-res-time-prov
               leaf tuning-mode
                 type enumeration
                 - Added enum: FAST
         rpc port-show-ptp
           output
             list output
             - Removed leaf: tx-oas
             - Removed leaf: rx-oas
             - Removed leaf: reach-type
             - Added leaf: rqst-tuning-mode
             - Added leaf: act-tuning-mode
               leaf tuning-mode
               - Changed type from enumeration to ciena-6500-enums:ochTuningMode
               leaf rqst-exp-res-time
                 type union
                   type ciena-6500-types:INT
                   - Added range: 0..100 
               leaf exp-res-time-prov
                 type ciena-6500-types:INT
                 - Added range: 0..100 
               leaf act-exp-res-time
                 type union
                   type ciena-6500-types:INT
                   - Added range: 0..100 
         rpc port-show-sttp
           output
             list output
               leaf sttp
               - Changed type from ciena-6500-types:aid to ciena-6500-types:IDENT
         container port
         - Added list: facgrp
         - Added list: facgrpmbr
           list ethn
           - Added leaf: mtu
           list otm
           - Added leaf: exp-res-time-prov
             leaf tuning-mode
               type enumeration
               - Added enum: FAST
           list ptp
           - Removed leaf: reach-type
           - Removed leaf: tx-oas
           - Removed leaf: rx-oas
           - Added leaf: rqst-tuning-mode
           - Added leaf: act-tuning-mode
             leaf tuning-mode
             - Changed default from NORMAL to UNKNOWN
             - Changed type from enumeration to ciena-6500-enums:ochTuningMode
             leaf exp-res-time-prov
               type ciena-6500-types:INT
               - Added range: 0..100 
             leaf rqst-exp-res-time
               type union
                 type ciena-6500-types:INT
                 - Added range: 0..100 
             leaf act-exp-res-time
               type union
                 type ciena-6500-types:INT
                 - Added range: 0..100 ";
  }
  revision 2018-08-03 {
    description
      "6500 Release 12.30 XR
       - Added rpc: port-show-sttp
       - Added rpc: port-disable-sttp
       - Added rpc: port-enable-sttp
       - Added rpc: port-operate-loopback-oductp
       - Added rpc: port-release-loopback-oductp
       - Added rpc: port-disable-cbrttp
       - Added rpc: port-enable-cbrttp
       - Added rpc: port-show-cbrttp
       - Added rpc: port-operate-loopback-cbrttp
       - Added rpc: port-release-loopback-cbrttp
         rpc port-show-eth10g
           output
             list output
               leaf-list sst
                 type enumeration
                 - Added enum: TSGEN
                 - Added enum: TSMON
         rpc port-show-ethn
           output
             list output
               leaf mapping
                 type enumeration
                 - Added enum: GFPFLEX
               leaf pre-fec-sf-th-lev
               - Changed type from ciena-6500-types:DECIMAL to decimal64
                 type decimal64
                 - Added range: -1.00..1.00 
               leaf pre-fec-sd-th-lev
               - Changed type from ciena-6500-types:DECIMAL to decimal64
                 type decimal64
                 - Added range: -1.00..2.00 
               leaf-list sst
                 type enumeration
                 - Added enum: TSMON
         rpc port-show-flex
           output
             list output
               leaf-list sst
                 type enumeration
                 - Added enum: TSGEN
                 - Added enum: TSMON
         rpc port-show-oc48
           output
             list output
             - Removed leaf: och-rx-act-power
             - Removed leaf: och-tx-act-power
             - Removed leaf: och-rx-min-power
             - Removed leaf: och-rx-max-power
             - Removed leaf: och-tx-min-power
             - Removed leaf: och-tx-max-power
             - Added leaf: rx-act-power
             - Added leaf: tx-act-power
             - Added leaf: rx-min-power
             - Added leaf: rx-max-power
             - Added leaf: tx-min-power
             - Added leaf: tx-max-power
         rpc port-show-oc192
           output
             list output
             - Removed leaf: och-rx-act-power
             - Removed leaf: och-rx-min-power
             - Removed leaf: och-rx-max-power
             - Removed leaf: och-tx-act-power
             - Removed leaf: och-tx-min-power
             - Removed leaf: och-tx-max-power
             - Removed leaf: ochtxwvlngthprov
             - Removed leaf: ochtxwvlngthmin
             - Removed leaf: ochtxwvlngthmax
             - Removed leaf: ochtxwvlngthspacing
             - Removed leaf: laserofffarendfail
             - Added leaf: rx-act-power
             - Added leaf: rx-min-power
             - Added leaf: rx-max-power
             - Added leaf: tx-act-power
             - Added leaf: tx-min-power
             - Added leaf: tx-max-power
             - Added leaf: tx-wvlngth-prov
             - Added leaf: tx-wvlngth-min
             - Added leaf: tx-wvlngth-max
             - Added leaf: tx-wvlngth-spacing
             - Added leaf: laser-off-far-end-fail
               leaf-list sst
                 type enumeration
                 - Added enum: TSGEN
                 - Added enum: TSMON
         rpc port-show-oc768
           output
             list output
             - Removed leaf: och-rx-act-power
             - Removed leaf: och-rx-min-power
             - Removed leaf: och-rx-max-power
             - Removed leaf: och-tx-act-power
             - Removed leaf: och-tx-min-power
             - Removed leaf: och-tx-max-power
             - Removed leaf: laserofffarendfail
             - Added leaf: rx-act-power
             - Added leaf: rx-min-power
             - Added leaf: rx-max-power
             - Added leaf: tx-act-power
             - Added leaf: tx-min-power
             - Added leaf: tx-max-power
             - Added leaf: laser-off-far-end-fail
               leaf-list sst
                 type enumeration
                 - Added enum: TSGEN
                 - Added enum: TSMON
         rpc port-show-otm2
           output
             list output
               leaf-list sst
                 type enumeration
                 - Added enum: TSGEN
                 - Added enum: TSMON
         rpc port-measure-rawber-otm2
           output
             list output
             - Removed leaf: och-rx-raw-ber
             - Added leaf: rx-raw-ber
         rpc port-show-otm3
           output
             list output
               leaf-list sst
                 type enumeration
                 - Added enum: TSGEN
                 - Added enum: TSMON
         rpc port-show-otm
           output
             list output
               leaf assoc-q
               - Changed type from ciena-6500-types:INT to union
                 type union
                 - Added type: enumeration
                 - Added type: ciena-6500-types:INT
               leaf-list sst
                 type enumeration
                 - Added enum: TSGEN
                 - Added enum: TSMON
         rpc port-show-ptp
           output
             list output
             - Added leaf: rqst-trans-mode
             - Added leaf: saved-trans-mode
             - Added leaf: rqst-linkOpt-mode
             - Added leaf: act-linkOpt-mode
             - Added leaf: saved-linkOpt-mode
             - Added leaf: rqst-tx-wvlngth
             - Added leaf: act-tx-wvlngth
             - Added leaf: rqst-tx-wvlngth-spacing
             - Added leaf: rqst-tx-freq
             - Added leaf: act-tx-freq
             - Added leaf: rqst-tx-pwr
             - Added leaf: rqst-tx-mode
             - Added leaf: act-tx-mode
             - Added leaf: rqst-tx-disp
             - Added leaf: act-tx-disp
             - Added leaf: rqst-path-disp
             - Added leaf: act-path-disp
             - Added leaf: rqst-carrier-centering-mode
             - Added leaf: act-carrier-centering-mode
             - Added leaf: rqst-laser-centering-range
             - Added leaf: act-laser-centering-range
             - Added leaf: rqst-ccda
             - Added leaf: act-ccda
             - Added leaf: rqst-och-tx-blanking
             - Added leaf: act-och-tx-blanking
             - Added leaf: rqst-line-type
             - Added leaf: rqst-allocated-spec-width
             - Added leaf: rqst-exp-res-time
             - Added leaf: exp-res-time-prov
             - Added leaf: act-exp-res-time
               leaf pre-fec-sf-th-lev
                 type decimal64
                 - Changed range from -1.0..1.0 to -1.00..1.00
               leaf pre-fec-sd-th-lev
                 type decimal64
                 - Changed range from -1.0..3.5 to -1.00..3.50
         rpc port-show-otuttp
           output
             list output
             - Removed leaf-list: pm-aid
         rpc port-show-oductp
           output
             list output
             - Added leaf: act-avail-ts
               leaf trib-slot-assignment
                 type string
                 - Changed length from 1..24 to 1..51
         container port
         - Added list: cbrttp
           container loopback
           - Added list: oductp
           - Added list: cbrttp
           list eth10g
             leaf-list sst
               type enumeration
               - Added enum: TSGEN
               - Added enum: TSMON
           list ethn
             leaf pre-fec-sf-th-lev
             - Changed type from ciena-6500-types:DECIMAL to decimal64
               type decimal64
               - Added range: -1.00..1.00 
             leaf pre-fec-sd-th-lev
             - Changed type from ciena-6500-types:DECIMAL to decimal64
               type decimal64
               - Added range: -1.00..2.00 
             leaf-list sst
               type enumeration
               - Added enum: TSMON
             leaf mapping
               type enumeration
               - Added enum: GFPFLEX
           list flex
             leaf-list sst
               type enumeration
               - Added enum: TSGEN
               - Added enum: TSMON
           list oc48
           - Removed leaf: och-rx-act-power
           - Removed leaf: och-tx-act-power
           - Removed leaf: och-rx-min-power
           - Removed leaf: och-rx-max-power
           - Removed leaf: och-tx-min-power
           - Removed leaf: och-tx-max-power
           - Removed leaf: laserofffarendfail
           - Added leaf: rx-act-power
           - Added leaf: tx-act-power
           - Added leaf: rx-min-power
           - Added leaf: rx-max-power
           - Added leaf: tx-min-power
           - Added leaf: tx-max-power
           - Added leaf: laser-off-far-end-fail
           list oc192
           - Removed leaf: laserofffarendfail
           - Removed leaf: ochtxwvlngthprov
           - Removed leaf: och-rx-act-power
           - Removed leaf: och-rx-min-power
           - Removed leaf: och-rx-max-power
           - Removed leaf: och-tx-act-power
           - Removed leaf: och-tx-min-power
           - Removed leaf: och-tx-max-power
           - Removed leaf: ochtxwvlngthmin
           - Removed leaf: ochtxwvlngthmax
           - Removed leaf: ochtxwvlngthspacing
           - Added leaf: laser-off-far-end-fail
           - Added leaf: tx-wvlngth-prov
           - Added leaf: rx-act-power
           - Added leaf: rx-min-power
           - Added leaf: rx-max-power
           - Added leaf: tx-act-power
           - Added leaf: tx-min-power
           - Added leaf: tx-max-power
           - Added leaf: tx-wvlngth-min
           - Added leaf: tx-wvlngth-max
           - Added leaf: tx-wvlngth-spacing
             leaf-list sst
               type enumeration
               - Added enum: TSGEN
               - Added enum: TSMON
           list oc768
           - Removed leaf: laserofffarendfail
           - Removed leaf: och-rx-act-power
           - Removed leaf: och-rx-min-power
           - Removed leaf: och-rx-max-power
           - Removed leaf: och-tx-act-power
           - Removed leaf: och-tx-min-power
           - Removed leaf: och-tx-max-power
           - Added leaf: laser-off-far-end-fail
           - Added leaf: rx-act-power
           - Added leaf: rx-min-power
           - Added leaf: rx-max-power
           - Added leaf: tx-act-power
           - Added leaf: tx-min-power
           - Added leaf: tx-max-power
             leaf-list sst
               type enumeration
               - Added enum: TSGEN
               - Added enum: TSMON
           list otm2
             leaf-list sst
               type enumeration
               - Added enum: TSGEN
               - Added enum: TSMON
           list otm3
             leaf-list sst
               type enumeration
               - Added enum: TSGEN
               - Added enum: TSMON
           list otm
             leaf-list sst
               type enumeration
               - Added enum: TSGEN
               - Added enum: TSMON
             leaf assoc-q
             - Changed type from ciena-6500-types:INT to union
               type union
               - Added type: enumeration
               - Added type: ciena-6500-types:INT
           list ptp
           - Added leaf: exp-res-time-prov
           - Added leaf: rqst-trans-mode
           - Added leaf: saved-trans-mode
           - Added leaf: rqst-linkOpt-mode
           - Added leaf: act-linkOpt-mode
           - Added leaf: saved-linkOpt-mode
           - Added leaf: rqst-tx-wvlngth
           - Added leaf: act-tx-wvlngth
           - Added leaf: rqst-tx-wvlngth-spacing
           - Added leaf: rqst-tx-freq
           - Added leaf: act-tx-freq
           - Added leaf: rqst-tx-pwr
           - Added leaf: rqst-tx-mode
           - Added leaf: act-tx-mode
           - Added leaf: rqst-tx-disp
           - Added leaf: act-tx-disp
           - Added leaf: rqst-path-disp
           - Added leaf: act-path-disp
           - Added leaf: rqst-carrier-centering-mode
           - Added leaf: act-carrier-centering-mode
           - Added leaf: rqst-laser-centering-range
           - Added leaf: act-laser-centering-range
           - Added leaf: rqst-ccda
           - Added leaf: act-ccda
           - Added leaf: rqst-och-tx-blanking
           - Added leaf: act-och-tx-blanking
           - Added leaf: rqst-line-type
           - Added leaf: rqst-allocated-spec-width
           - Added leaf: rqst-exp-res-time
           - Added leaf: act-exp-res-time
             leaf pre-fec-sf-th-lev
               type decimal64
               - Changed range from -1.0..1.0 to -1.00..1.00
             leaf pre-fec-sd-th-lev
               type decimal64
               - Changed range from -1.0..3.5 to -1.00..3.50
           list otuttp
           - Removed leaf-list: pm-aid
           list sttp
             leaf rate
             - Added mandatory: true 
             - Changed config from false to true
             leaf pst
             - Changed config from false to true
             - Changed type from ciena-6500-enums:PSTfac_RTRV to enumeration
               type enumeration
               - Added enum: IS
               - Added enum: OOS-MA
               - Added enum: IS-ANR
               - Added enum: OOS-AU
               - Added enum: OOS-AUMA
               - Added enum: OOS-MAANR
           list oductp
           - Added leaf: act-avail-ts
             leaf trib-slot-assignment
               type string
               - Changed length from 1..24 to 1..51
             leaf ex-pt
             - Changed config from false to true
           list tcm
             leaf sd-th
             - Changed config from false to true
               type ciena-6500-types:INT
               - Changed range from 5..9 to 6..9";
  }
  revision 2017-12-18 {
    description
      "6500 Release 12.20 PX
         rpc port-show-otm
           output
             list output
             - Added leaf: laser-freq-thr
         container port
           list otm
           - Added leaf: laser-freq-thr
           list ptp
             leaf laser-freq-thr
             - Changed default from 1.5 to 1.6
             leaf-list sst
               type enumeration
               - Added enum: TSRECIRC
           list otuttp
             leaf-list sst
               type enumeration
               - Added enum: TSRECIRC
           list ettp
             leaf-list sst
               type enumeration
               - Added enum: TSRECIRC
           list tcm
             leaf-list sst
               type enumeration
               - Added enum: TSRECIRC";
  }
  revision 2017-09-18 {
    description
      "6500 Release 12.10 FX
       - Added rpc: port-disable-eth
       - Added rpc: port-disable-eth100
       - Added rpc: port-enable-eth
       - Added rpc: port-enable-eth100
       - Added rpc: port-disable-wan
       - Added rpc: port-enable-wan
       - Added rpc: port-show-wan
       - Added rpc: port-show-eth10g
       - Added rpc: port-show-ethn
       - Added rpc: port-disable-lag
       - Added rpc: port-enable-lag
       - Added rpc: port-delete-lag-port
       - Added rpc: port-enable-fiber-channel
       - Added rpc: port-disable-fiber-channel
       - Added rpc: port-show-flex
       - Added rpc: port-enable-flex
       - Added rpc: port-disable-flex
       - Added rpc: port-disable-oc3
       - Added rpc: port-enable-oc3
       - Added rpc: port-show-oc3
       - Added rpc: port-disable-oc12
       - Added rpc: port-enable-oc12
       - Added rpc: port-show-oc12
       - Added rpc: port-disable-oc48
       - Added rpc: port-enable-oc48
       - Added rpc: port-show-oc48
       - Added rpc: port-disable-oc192
       - Added rpc: port-enable-oc192
       - Added rpc: port-show-oc192
       - Added rpc: port-disable-oc768
       - Added rpc: port-enable-oc768
       - Added rpc: port-show-oc768
       - Added rpc: port-show-otm2
       - Added rpc: port-init-dispscan-otm2
       - Added rpc: port-measure-rawber-otm2
       - Added rpc: port-show-otm3
       - Added rpc: port-show-otm
       - Added rpc: port-init-dispscan-otm
       - Added rpc: port-show-sts192c
       - Added rpc: port-show-tti-odu
       - Added rpc: port-show-trace-flex
       - Added rpc: port-show-ptp
       - Added rpc: port-disable-ptp
       - Added rpc: port-enable-ptp
       - Added rpc: port-init-dispscan-ptp
       - Added rpc: port-show-otuttp
       - Added rpc: port-disable-otuttp
       - Added rpc: port-enable-otuttp
       - Added rpc: port-operate-loopback-otuttp
       - Added rpc: port-release-loopback-otuttp
       - Added rpc: port-operate-loopback-sttp
       - Added rpc: port-release-loopback-sttp
       - Added rpc: port-show-ettp
       - Added rpc: port-disable-ettp
       - Added rpc: port-enable-ettp
       - Added rpc: port-operate-loopback-ettp
       - Added rpc: port-release-loopback-ettp
       - Added rpc: port-show-oduttp
       - Added rpc: port-disable-oduttp
       - Added rpc: port-enable-oduttp
       - Added rpc: port-operate-loopback-oduttp
       - Added rpc: port-release-loopback-oduttp
       - Added rpc: port-show-oductp
       - Added rpc: port-delete-oductp
       - Added rpc: port-disable-oductp
       - Added rpc: port-enable-oductp
       - Added rpc: port-show-tcm
       - Added rpc: port-disable-tcm
       - Added rpc: port-enable-tcm
       - Added rpc: port-show-odu
       - Added rpc: port-disable-odu
       - Added rpc: port-enable-odu
         container port
         - Added container: loopback
         - Added container: trace
         - Added container: tti
         - Added container: wavelength
         - Added list: eth
         - Added list: eth100
         - Added list: lag
         - Added list: lag-port
         - Added list: fiber-channel
         - Added list: oc3
         - Added list: oc12
         - Added list: oc48
         - Added list: oc192
         - Added list: oc768
         - Added list: sts192c
         - Added list: ptp
         - Added list: otuttp
         - Added list: fttp
         - Added list: sttp
         - Added list: ettp
         - Added list: oduttp
         - Added list: oductp
         - Added list: tcm
         - Added list: pc
         - Added list: vcp
           list wan
             leaf wan
             - Added mandatory: true 
             - Changed type from ciena-6500-types:IDENT to ciena-6500-types:aid
             leaf fcs
             - Added default: 0 
             leaf scramble
               type enumeration
               - Added enum: DISABLE
             leaf mapping
             - Added default: GFP-F 
               type enumeration
               - Added enum: POS
             leaf lcas
             - Added default: DISABLE 
             leaf cond-type
             - Changed type from ciena-6500-enums:Conditioning to enumeration
               type enumeration
               - Added enum: NONE
               - Added enum: GFPCMF
               - Added enum: GFPCMFUSER
               - Added enum: GFP10BERR
               - Added enum: UNEQ
               - Added enum: NILTR
               - Added enum: AIS
               - Added enum: GFPCSF
             leaf if-type
             - Added mandatory: true 
             leaf policing
             - Added default: ENABLE 
             leaf loop-detect
             - Added default: DISABLE 
             leaf bw-threshld
               type ciena-6500-types:INT
               - Added range: 1..100 
             leaf gfp-rfi-upi
               type ciena-6500-types:INT
               - Added range: 3..255 
             leaf user-rx-cos
               type ciena-6500-types:INT
               - Added range: 0..15 
             leaf pbt-list-sup
               type ciena-6500-types:INT
               - Added range: 0 | 1 
             leaf pst
             - Added default: OOS-MA 
             - Changed config from false to true
             leaf prov-units
               type ciena-6500-types:INT
               - Added range: 0..64 
             leaf prov-rx-units
               type ciena-6500-types:INT
               - Added range: 0..64 
             leaf actual-units
               type ciena-6500-types:INT
               - Added range: 0..64 
             leaf max-vc-del
               type ciena-6500-types:INT
               - Added range: 0..256000 
             leaf curr-vc-del
               type ciena-6500-types:INT
               - Added range: 0..256000 
             leaf round-trip-delay
               type ciena-6500-types:INT
               - Added range: 0..220000 
             leaf actual-rx-units
               type ciena-6500-types:INT
               - Added range: 0..64 
             leaf bw-remain
               type ciena-6500-types:INT
               - Added range: 1..2500000 
             leaf bw-utl
               type ciena-6500-types:INT
               - Added range: 0..100 
             leaf snmp-index
               type ciena-6500-types:INT
               - Added range: 0..4294967295 
             leaf force
             - Added default: NO 
           list eth10g
           - Removed leaf: suto-neg
             leaf eth10g
             - Added mandatory: true 
             - Changed type from ciena-6500-types:IDENT to ciena-6500-types:aid
             leaf laser-off-far-end-fail
             - Added default: DISABLED 
             leaf auto-neg
             - Added default: DISABLE 
             leaf pause-tx
             - Added default: ENABLE 
             leaf speed
             - Added default: 10G 
             leaf eth-duplex
             - Added default: FULL 
             leaf tx-con
             - Added default: ENABLE 
             leaf tx-inter-pkt-gap
             - Added default: 12 
             leaf tx-con-hb
             - Added default: ENABLE 
             leaf tx-con-hb-interval
             - Added default: 1SEC 
             leaf tx-con-md-level
             - Added default: 0 
               type ciena-6500-types:INT
               - Added range: 0..7 
             leaf tx-cond-network-flt-sig
             - Added default: EXPLICIT 
             leaf eqpt
             - Added default: XGELAN 
             leaf pause-tx-override
             - Added default: DISABLE 
             leaf rx-idle
             - Added default: 0 
             leaf dus-override
             - Added default: DISABLE 
             leaf user-rx-cos
               type ciena-6500-types:INT
               - Added range: 0..15 
             leaf pbt-list-sup
               type ciena-6500-types:INT
               - Added range: 0 | 1 
             leaf rate
               type ciena-6500-types:INT
               - Added range: 10 | 20 | 30..10000 
             leaf hold-off
               type ciena-6500-types:INT
               - Added range: 0 | 100 | 200 | 300 | 400 | 500 | 600 | 700 | 800 | 900 | 1000 
             leaf-list sst
               type enumeration
               - Added enum: AINS-DEA
             leaf mapping
             - Added default: GFPSTD 
             leaf mode
             - Added default: L2 
             leaf pst
             - Added default: IS 
             leaf tx-wvlngth-min
             - Added default: 0.00 
             leaf tx-wvlngth-max
             - Added default: 0.00 
           list ethn
           - Added leaf: hold-off
             leaf ethn
             - Added mandatory: true 
             - Changed type from ciena-6500-types:IDENT to ciena-6500-types:aid
             leaf laser-off-far-end-fail
             - Added default: DISABLED 
             leaf pre-fec-sf-th-lev
             - Changed type from ciena-6500-types:STRING to ciena-6500-types:DECIMAL
               type ciena-6500-types:DECIMAL
               - Added range: -1 | 0 | 1 
             leaf pre-fec-sd-th-lev
             - Changed type from ciena-6500-types:STRING to ciena-6500-types:DECIMAL
               type ciena-6500-types:DECIMAL
               - Added range: -1.0..2.0 
             leaf-list sst
               type enumeration
               - Added enum: AINS-DEA
               - Added enum: TSGEN
             leaf mapping
               type enumeration
               - Added enum: PROPRIETARY
             leaf pst
             - Added default: IS 
           list flex
             leaf flex
             - Added mandatory: true 
             - Changed type from ciena-6500-types:IDENT to ciena-6500-types:aid
             leaf protocol
             - Added mandatory: true 
             leaf latency-opt
             - Added default: MEDIUM 
             leaf hold-off
               type ciena-6500-types:INT
               - Added range: 0 | 100 | 200 | 300 | 400 | 500 | 600 | 700 | 800 | 900 | 1000 
             leaf tf-mode
             - Added default: OFF 
             leaf ing-police
             - Added default: DISABLED 
             leaf cir
             - Added default: 1 
               type ciena-6500-types:INT
               - Added range: 1..1000000 
             leaf cbs
             - Added default: 12176 
               type ciena-6500-types:INT
               - Added range: 1..131071 
             leaf cbs-units
             - Added default: BYTE 
             leaf-list sst
               type enumeration
               - Added enum: AINS-DEA
           list otm2
           - Removed leaf: otu-term
           - Added leaf: otm-term
             leaf otm2aid
             - Added mandatory: true 
             - Changed type from ciena-6500-types:IDENT to ciena-6500-types:aid
             leaf tx-sbs
             - Added default: ON 
             leaf tx-am-frmt
             - Added default: AM2 
             leaf tx-path-id
               type ciena-6500-types:INT
               - Added range: 1..254 
             leaf tx-tr-cont
             - Added default: ON 
             leaf tx-mode
             - Added default: ED 
             leaf tx-wvlngth-prov
             - Added default: 0.00 
             leaf tx-disp-prov
             - Added default: 0 
             leaf tf-mode
             - Added default: OFF 
               type enumeration
               - Added enum: LINEFAIL
             leaf odu-tf-mode
             - Added default: OFF 
             leaf otu-timen
             - Added default: OPERATOR 
             leaf odu-timen
             - Added default: OPERATOR 
             leaf laser-off-far-end-fail
             - Added default: DISABLED 
             leaf tx-chrip
             - Added default: NEGATIVE 
             leaf otu-rate
             - Added default: 10G709 
             leaf odu-sf-th-lev
             - Added default: 0 
             leaf odu-sd-th-lev
             - Added default: 0 
             leaf cc-tx-msg-len
             - Added default: 16 
             leaf rc-rx-msg-len
             - Added default: 28 
             leaf rc-rx-ask-baud-rate
             - Added default: 16.67 
             leaf rc-rx-decode-frmt
             - Added default: 3SB1 
             leaf rc-rx-thresh-mode
             - Added default: AUTO 
             leaf rc-rx-thresh
             - Added default: 100 
             leaf dm-enable
             - Added default: NO 
             leaf encr-tcm
             - Added default: 1 
               type ciena-6500-types:INT
               - Added range: 1..6 
             leaf spli-mgmt
             - Added default: ON 
             leaf pst
             - Added default: IS 
             leaf-list sst
               type enumeration
               - Added enum: AINS-DEA
             leaf tx-wvlngth-min
             - Added default: 0.00 
             leaf tx-wvlngth-max
             - Added default: 0.00 
             leaf tx-act-disp
             - Changed type from ciena-6500-types:INT to union
               type union
               - Added type: enumeration
               - Added type: ciena-6500-types:INT
             leaf rx-act-disp
             - Changed type from ciena-6500-types:INT to union
               type union
               - Added type: enumeration
               - Added type: ciena-6500-types:INT
             leaf force
             - Added default: NO 
           list otm3
           - Removed leaf: otu-term
           - Added leaf: otm-term
             leaf otm3aid
             - Added mandatory: true 
             - Changed type from ciena-6500-types:IDENT to ciena-6500-types:aid
             leaf tx-path-id
               type ciena-6500-types:INT
               - Added range: 1..254 
             leaf tx-wvlngth-prov
             - Added default: 0.00 
             leaf tf-mode
             - Added default: OFF 
               type enumeration
               - Added enum: LINEFAIL
             leaf odu-tf-mode
             - Added default: OFF 
             leaf otu-timen
             - Added default: OPERATOR 
             leaf odu-timen
             - Added default: OPERATOR 
             leaf laser-off-far-end-fail
             - Added default: DISABLED 
             leaf pwr-bal-ctlr
             - Added default: DISABLED 
             leaf tuning-mode
             - Added default: NORMAL 
             leaf odu-handoff
             - Added default: AUTO 
             leaf frr
             - Added default: DISABLED 
             leaf frr-config
             - Added default: MATCHEDCD 
             leaf frr-path1-disp
             - Added default: AUTO 
             leaf frr-path2-disp
             - Added default: AUTO 
             leaf dm-enable
             - Added default: NO 
             leaf spli-mgmt
             - Added default: ON 
             leaf pst
             - Added default: IS 
             leaf-list sst
               type enumeration
               - Added enum: AINS-DEA
             leaf tx-wvlngth-min
             - Added default: 0.00 
             leaf tx-wvlngth-max
             - Added default: 0.00 
             leaf rx-act-disp
             - Changed type from ciena-6500-types:INT to union
               type union
               - Added type: enumeration
               - Added type: ciena-6500-types:INT
             leaf odu-sf-th-lev
             - Added default: 0 
             leaf odu-sd-th-lev
             - Added default: 0 
             leaf hold-off
             - Added default: 0 
             leaf hold-on
             - Added default: 0 
             leaf force
             - Added default: NO 
           list otminfo
             leaf otmnaid
             - Added mandatory: true 
             - Changed type from ciena-6500-types:IDENT to ciena-6500-types:aid
           list otm
           - Removed leaf: otu-term
           - Added leaf: otm-term
             leaf otmaid
             - Added mandatory: true 
             - Changed type from ciena-6500-types:IDENT to ciena-6500-types:aid
             leaf tx-path-id
               type ciena-6500-types:INT
               - Added range: 1..254 
             leaf tx-wvlngth-prov
             - Added default: 0.00 
             leaf tx-wvlngth-spacing
             - Added default: 50 
             leaf odu-handoff
             - Added default: AUTO 
             leaf tf-mode
             - Added default: OFF 
               type enumeration
               - Added enum: LINEFAIL
             leaf odu-tf-mode
             - Added default: OFF 
             leaf otu-timen
             - Added default: OPERATOR 
             leaf odu-timen
             - Added default: OPERATOR 
             leaf laser-off-far-end-fail
             - Added default: DISABLED 
             leaf frr
             - Added default: DISABLED 
             leaf frr-config
             - Added default: MATCHEDCD 
             leaf frr-path1-disp
             - Added default: AUTO 
             leaf frr-path2-disp
             - Added default: AUTO 
             leaf odu-sf-th-lev
             - Added default: 0 
             leaf odu-sd-th-lev
             - Added default: 0 
             leaf otu-rate
               type enumeration
               - Added enum: OTUC2
             leaf dm-enable
             - Added default: NO 
             leaf spli-mgmt
             - Added default: ON 
             leaf encr-tcm
             - Added default: 1 
               type ciena-6500-types:INT
               - Added range: 1..6 
             leaf rx-pwr-l-thr
             - Added default: 0 
             leaf rx-pwr-h-thr
             - Added default: 0 
             leaf rx-ch-pwr-l-thr
             - Added default: 0 
             leaf rx-ch-pwr-h-thr
             - Added default: 0 
             leaf rx-pwr-thr-prov
             - Added default: OFF 
             leaf laser-centering-range
             - Added default: 2.5 Ghz 
             leaf pst
             - Added default: IS 
             leaf-list sst
               type enumeration
               - Added enum: AINS-DEA
             leaf tx-act-disp
             - Changed type from ciena-6500-types:INT to union
               type union
               - Added type: enumeration
               - Added type: ciena-6500-types:INT
             leaf rx-act-disp
             - Changed type from ciena-6500-types:INT to union
               type union
               - Added type: enumeration
               - Added type: ciena-6500-types:INT
             leaf tx-pre-disp
             - Changed type from ciena-6500-types:INT to union
               type union
               - Added type: enumeration
               - Added type: ciena-6500-types:INT
             leaf rx-post-disp
             - Changed type from ciena-6500-types:INT to union
               type union
               - Added type: enumeration
               - Added type: ciena-6500-types:INT
             leaf tx-wvlngth-min
             - Added default: 0.00 
             leaf tx-wvlngth-max
             - Added default: 0.00 
             leaf hold-off
             - Added default: 0 
             leaf hold-on
             - Added default: 0 
             leaf tx-disp-found
             - Changed type from ciena-6500-types:INT to union
               type union
               - Added type: enumeration
               - Added type: ciena-6500-types:INT
             leaf tx-freq-min
             - Added default: 0.00 
             leaf tx-freq-max
             - Added default: 0.00 
             leaf force
             - Added default: NO 
           list odu
             leaf odun
             - Added mandatory: true 
             - Changed type from ciena-6500-types:IDENT to ciena-6500-types:aid
             leaf odu-tf-mode
             - Added default: OFF 
             leaf odu-timen
             - Added default: OPERATOR 
             leaf odu-monitor
             - Added default: NO 
             leaf encryption-tcm
             - Added default: 1 
               type ciena-6500-types:INT
               - Added range: 1..6 
             leaf-list sst
             - Changed type from ciena-6500-enums:SSTODU to enumeration
               type enumeration
               - Added enum: AINS
               - Added enum: AINS-DEA
               - Added enum: ACT
               - Added enum: IDLE
               - Added enum: STBYS
               - Added enum: WRK
               - Added enum: FLT
               - Added enum: MEA
               - Added enum: UEQ
               - Added enum: SGEO
               - Added enum: DISCD
               - Added enum: LPBK
               - Added enum: TS
               - Added enum: STBYH
               - Added enum: WRKRX
               - Added enum: WRKTX
               - Added enum: UAS
               - Added enum: PROTECTED
               - Added enum: MT
               - Added enum: DSBLD";
  }
  revision 2016-07-21 {
    description
      "6500 Release 11.20 SV
       - Added container: port
       - Added rpc: port-enable-eth10g
       - Added rpc: port-disable-eth10g
       - Added rpc: port-enable-ethn
       - Added rpc: port-disable-ethn
       - Added rpc: port-disable-otm2
       - Added rpc: port-enable-otm2
       - Added rpc: port-disable-otm3
       - Added rpc: port-enable-otm3
       - Added rpc: port-disable-otm
       - Added rpc: port-enable-otm";
  }

  rpc port-disable-wan {
    description
      "Remove WAN Facility: This command allows you to remove the specified facility from service and put it in an out-of-service for maintenance state";
    yang:handler "tl1";
    input {
      leaf wan {
        mandatory true;
        description
          "AID in format WAN-shelf-slot-port-rt1Ptp1, WAN-shelf-slot-portSsubport-rt1Ptp1";
        type ciena-6500-types:aid;
      }
    }
  }

  rpc port-enable-wan {
    description
      "Restore WAN Facility: This command allows you to restore a facility to service. The facility goes from a maintenance state to an in-service state.";
    yang:handler "tl1";
    input {
      leaf wan {
        mandatory true;
        description
          "AID in format WAN-shelf-slot-port-rt1Ptp1, WAN-shelf-slot-portSsubport-rt1Ptp1";
        type ciena-6500-types:aid;
      }
    }
  }

  rpc port-show-wan {
    description
      "Retrieve WAN Facility attributes.";
    yang:handler "tl1";
    input {
      leaf wan {
        mandatory true;
        description
          "AID in format WAN-shelf-slot-port, WAN-shelf-slot-portSsubport, WAN10G-shelf-slot-portSsubport, WAN-shelf-slot-port-rt1Ptp1, WAN-shelf-slot-port-rt1Ptp1-rt2Ptp2, WAN-shelf-slot-port-rt1Ptp1-rt2Ptp2-rt3Ptp3, WAN-shelf-slot-port-rt1Ptp1-rt2Ptp2-rt3Ptp3-rt4Ptp4, WAN-shelf-slot-portSsubport-rt1Ptp1, WAN-shelf-slot-portSsubport-rt1Ptp1-rt2Ptp2, WAN-shelf-slotSsubslot-portSsubport, WAN-shelf-slotSsubslot-port, WAN-shelf-slotSsubslot-portSsubport-rt1Ptp1, WAN-shelf-slotSsubslot-portSsubport-rt1Ptp1-rt2Ptp2, WAN-shelf-slotSsubslot-port-rt1Ptp1, WAN-shelf-slotSsubslot-port-rt1Ptp1-rt2Ptp2, WAN-shelf-slotSsubslot-port-rt1Ptp1-rt2Ptp2-rt3Ptp3";
        type ciena-6500-types:aid;
      }
      leaf stats-info {
        yang:get-supported "true";
        type enumeration {
          enum NO {
            description
              "Do not include Dynamic Status information in the response";
          }
          enum YES {
            description
              "Include Dynamic Status information in the response";
          }
        }
        description
          "Specify if Dynamic Status Information is to be included in the response";
      }
    }
    output {
      list output {
        leaf wan {
          yang:get-supported "true";
          type ciena-6500-types:IDENT;
          description
            "aid";
        }
        leaf mapping {
          yang:get-supported "true";
          type enumeration {
            enum GFP-F;
            enum GFP-T;
          }
          description
            "Packet mapping into SONET/SDH";
        }
        leaf mode {
          yang:get-supported "true";
          type enumeration {
            enum SDH;
            enum SONET;
          }
          description
            "Indicates the current mode (either SONET or SDH).";
        }
        leaf rate {
          yang:get-supported "true";
          type enumeration {
            enum NONE {
              description
                "SONET/SDH Basic rate derived from SONET/SDH cross-connections";
            }
            enum STS1 {
              description
                "SONET/SDH Basic rate derived from SONET/SDH cross-connections";
            }
            enum STS3C {
              description
                "SONET/SDH Basic rate derived from SONET/SDH cross-connections";
            }
            enum STS6C {
              description
                "SONET/SDH Basic rate derived from SONET/SDH cross-connections";
            }
            enum STS9C {
              description
                "SONET/SDH Basic rate derived from SONET/SDH cross-connections";
            }
            enum STS12C {
              description
                "SONET/SDH Basic rate derived from SONET/SDH cross-connections";
            }
            enum STS24C {
              description
                "SONET/SDH Basic rate derived from SONET/SDH cross-connections";
            }
            enum STS48C {
              description
                "SONET/SDH Basic rate derived from SONET/SDH cross-connections";
            }
            enum STS192C {
              description
                "SONET/SDH Basic rate derived from SONET/SDH cross-connections";
            }
            enum VT1 {
              description
                "SONET/SDH Basic rate derived from SONET/SDH cross-connections";
            }
            enum VT2 {
              description
                "SONET/SDH Basic rate derived from SONET/SDH cross-connections";
            }
          }
          description
            "SONET/SDH Basic rate (derived from SONET/SDH cross-connections)";
        }
        leaf-list vcat {
          yang:get-supported "true";
          type enumeration {
            enum ENABLE;
            enum GROUPED {
              description
                "Grouped switching enabled (from dual sources).";
            }
            enum DISABLE;
          }
          description
            "SONET/SDH concatenation";
        }
        leaf-list pdh-type {
          yang:get-supported "true";
          type ciena-6500-enums:PDHTYPE_LIST;
          description
            "Accociated PDH channel type";
        }
        leaf lcas {
          yang:get-supported "true";
          type enumeration {
            enum DISABLE;
            enum ENABLE {
              description
                "Only if VCAT is ENABLE";
            }
          }
          description
            "Link Capacity Adjustment Scheme Mode";
        }
        leaf prov-units {
          yang:get-supported "true";
          type ciena-6500-types:INT {
            range "0..64";
          }
          description
            "Used to indicate the number of provisioned bandwidth units (of rate specified by the RATE attribute). Number of provisioned bandwidth units (RATE attributes). For contiguous concatenation, allowable values are either 0 or 1. The information is derived from the cross connection(s).";
        }
        leaf prov-rx-units {
          yang:get-supported "true";
          type ciena-6500-types:INT {
            range "0..64";
          }
          description
            "Indicate the current number of provisioned members in the receive direction.";
        }
        leaf actual-units {
          yang:get-supported "true";
          type ciena-6500-types:INT {
            range "0..64";
          }
          description
            "Indicates the number of bandwidth units actually carrying traffic. For contiguous concatenation, or for virtual concatenation without LCAS enabled, allowable values are either 0 or PROVUNITS. With LCAS enabled, allowable values are 0 to PROVUNITS. If the value cannot be retrieved, UNKNOWN will be displayed.";
        }
        leaf magic-num {
          yang:get-supported "true";
          type enumeration {
            enum DISABLE;
            enum ENABLE;
          }
          description
            "Enables or disables the use of a magic number to distinguish between two peers and detect error conditions. Can be used to determine whether trying to establish a link with one self. Default value is Enable for MAPPING=POS, and Disable for MAPPING=GFP-F or GFP-T. For MAPPING=GFP-F or GFP-T, only possible value is Disable.";
        }
        leaf fcs {
          yang:get-supported "true";
          type enumeration {
            enum 0;
            enum 16;
            enum 32;
          }
          description
            "Frame Checksum. For MAPPING=POS, value can be 16 or 32. For MAPPING=GFP-F, value can be 0 or 32. For MAPPING=GFP-T, only possible value is 0.";
        }
        leaf scramble {
          yang:get-supported "true";
          type enumeration {
            enum ENABLE;
          }
          description
            "Used to control payload X^43+1 payload scrambling.";
        }
        leaf lcm {
          yang:get-supported "true";
          type enumeration {
            enum DISABLE;
            enum ENABLE;
          }
          description
            "Link Connectivity Monitor. In some circumstances it may be desirable to disable the link continuity monitor (LCM). When enabled, LCM sends an echo request every second. If more than five echo requests are transmitted without receiving an echo response, the PPP operational OSI state becomes disabled, and PPP attempts to re-establish the link connection via LCP configuration request packets. Default value is Enable for MAPPING=POS, and Disable for MAPPING=GFP-F or GFP-T. For MAPPING=GFP-F or GFP-T, only possible value is Disable.";
        }
        leaf ncp {
          yang:get-supported "true";
          type enumeration {
            enum NONE;
            enum BCP;
          }
          description
            "Used to indicate the Network Control Protocol used. BCP is returned when MAPPING=POS, and NONE is returned when MAPPING=GFP=F or GFP-T.";
        }
        leaf max-vc-del {
          yang:get-supported "true";
          type ciena-6500-types:INT {
            range "0..256000";
          }
          description
            "Maximum differential delay supported by the port in microseconds. If the value cannot be retrieved, UNKNOWN will be displayed.";
        }
        leaf curr-vc-del {
          yang:get-supported "true";
          type ciena-6500-types:INT {
            range "0..256000";
          }
          description
            "Current differential delay in microseconds. If the value cannot be retrieved, UNKNOWN will be displayed. If VCAT is disabled or if WAN is not cross-connected, NA (Not Applicable) will be displayed.";
        }
        leaf lan-fcs {
          yang:get-supported "true";
          type enumeration {
            enum DISABLE;
            enum ENABLE;
          }
          description
            "Indicates whether the LAN FCS is included in the encapsulated frame (for both the ingress and egress direction). Enable indicates the LAN FCS is included. Default value is Enable for MAPPING=POS, and Disable for MAPPING=GFP-F or GFP-T. For MAPPING=GFP-F or GFP-T, only possible value is Disable.";
        }
        leaf round-trip-delay {
          yang:get-supported "true";
          type ciena-6500-types:INT {
            range "0..220000";
          }
          description
            "Round Trip Delay in microseconds. If the value cannot be retrieved, UNKNOWN will be displayed.";
        }
        leaf actual-rx-units {
          yang:get-supported "true";
          type ciena-6500-types:INT {
            range "0..64";
          }
          description
            "Current number of active members in the receive direction. When LCAS is disabled, allowable values are either 0 or PROVRXUNITS. With LCAS enabled, allowable values are 0 to PROVRXUNITS. If the value cannot be retrieved, UNKNOWN will be displayed.";
        }
        leaf gfp-rfi {
          yang:get-supported "true";
          type enumeration {
            enum ENABLE {
              description
                "(Default) Transmit GFP RFI CMF on WAN link down.";
            }
            enum DISABLE {
              description
                " Do not transmit CMF UPI on WAN link down.";
            }
            enum CMFCSF {
              description
                "Transmit GFP CSF CMF on WAN link down.";
            }
            enum USERDEF {
              description
                "The provisioned UPI value to be transmitted on WAN link down.";
            }
          }
          description
            "The state of the transmission of GFP Client Signal Fail (CSF) CMFs.";
        }
        leaf gfp-rfi-upi {
          yang:get-supported "true";
          type ciena-6500-types:INT {
            range "3..255";
          }
          description
            "The provisioned UPI value to be transmitted on WAN link down.";
        }
        leaf gfp-cmf-upi {
          yang:get-supported "true";
          type ciena-6500-types:STRING;
          description
            "HEX value in the range 0x03-0xFF. UPI to be transmitted in GFP client management frames.";
        }
        leaf gfp-rt-delay {
          yang:get-supported "true";
          type ciena-6500-enums:ENABLE_DISABLE;
          description
            "DISABLE means the ping CMFs used for RTDELAY calculation and Distance Exceeded Alarm will no longer be sent. This implies RTDELAY will always display UNKNOWN and the Distance Exceeded Alarm will never raise.";
        }
        leaf cond-type {
          yang:get-supported "true";
          type ciena-6500-enums:Conditioning;
          description
            "This attribute is used to control the type of WAN conditioning applied to WAN upon LAN defects (Rx Loss of Signal, Rx Loss of Sync, AN time-out, Rx Idle, Link Down) and CP Fail. Possible values are NONE or a combination of: GFPCMF, GFPCMFUSER, GFP10BERR, UNEQ, AIS and NILTR.";
        }
        leaf if-type {
          yang:get-supported "true";
          type enumeration {
            enum UNI;
            enum NNI;
          }
          description
            "The type of the WAN facility being queried";
        }
        leaf policing {
          yang:get-supported "true";
          type enumeration {
            enum ENABLE;
            enum DISABLE;
          }
          description
            "Indicates whether policing will be done on the given port";
        }
        leaf e-type {
          yang:get-supported "true";
          type string {
            length "1..4";
          }
          description
            "Encapsulation scheme used in customer frames";
        }
        leaf p-mode {
          yang:get-supported "true";
          type enumeration {
            enum PBITS;
            enum TOS;
          }
          description
            "(DEPRECATED) Priority Mode";
        }
        leaf dm-prf {
          yang:get-supported "true";
          type ciena-6500-types:STRING;
          description
            "(DEPRECATED) Discard Marking Profile";
        }
        leaf cf-prf {
          yang:get-supported "true";
          type ciena-6500-types:STRING;
          description
            "The AID of the port Control Frame Profile (CFPRF-shelf-profileNo)";
        }
        leaf sch-prf {
          yang:get-supported "true";
          type ciena-6500-types:STRING;
          description
            "(DEPRECATED) Scheduler Profiler";
        }
        leaf loop-detect {
          yang:get-supported "true";
          type enumeration {
            enum ENABLE;
            enum DISABLE;
          }
          description
            "Loopback Detection using SONMP.";
        }
        leaf bw-threshld {
          yang:get-supported "true";
          type ciena-6500-types:INT {
            range "1..100";
          }
          description
            "The bandwidth utilization percentage threshold ";
        }
        leaf-list available-rate {
          yang:get-supported "true";
          type enumeration {
            enum RATE {
              description
                "The available bandwidth for a given port (in SONET/SDH Basic RATE) For Ex : In GE card VCAT=ENABLE. AVLBLRATE on all WAN ports is STS1LO/STS1HO/STS3C ";
            }
          }
          description
            "Used to indicate the available bandwidth rate in the wan port.";
        }
        leaf bw-remain {
          yang:get-supported "true";
          type ciena-6500-types:INT {
            range "1..2500000";
          }
          description
            "The unused bandwidth remained for a given port (in KBIT)";
        }
        leaf bw-utl {
          yang:get-supported "true";
          type ciena-6500-types:INT {
            range "0..100";
          }
          description
            "The port bandwidth utilization percentage";
        }
        leaf snmp-index {
          yang:get-supported "true";
          type ciena-6500-types:INT {
            range "0..4294967295";
          }
          description
            "Identifies the index of the equivalent entry in the SNMP interfaces MIB group";
        }
        leaf preamble {
          yang:get-supported "true";
          type enumeration {
            enum KEEP {
              description
                "Keep Ethernet preamble.";
            }
            enum DISCARD {
              description
                "Discard Ethernet preamble.";
            }
          }
          description
            "This attribute is used to specify whether to use the preamble at beginning of GFP frame or throw it away. The preamble is 8 bytes in total (7 bytes + 1 byte sfd).";
        }
        leaf opu2-resvd {
          yang:get-supported "true";
          type enumeration {
            enum YES {
              description
                "Use 7 unused bytes of the OPU2 overhead for payload.";
            }
            enum NO {
              description
                "Do not use 7 unused bytes of the OPU2 overhead for payload";
            }
          }
          description
            "This attribute is used to specify whether to use the 7 unused bytes of the OPU2 overhead for payload or not.";
        }
        leaf fcs-err-frames {
          yang:get-supported "true";
          type enumeration {
            enum KEEP {
              description
                "Keep FCS-errored frames end-to-end.";
            }
            enum DISCARD {
              description
                "Discard FCS-errored frames end-to-end.";
            }
          }
          description
            "This attribute is used to specify whether to keep FCS-errored frames or Ethernet frames end-to-end or to discard them.";
        }
        leaf received-pt {
          yang:get-supported "true";
          type ciena-6500-types:STRING;
          description
            "HEX value in the range 0x00-0xFF. This attribute is used for Received PT";
        }
        leaf tx-pt {
          yang:get-supported "true";
          type ciena-6500-types:STRING;
          description
            "HEX value in the range 0x00-0xFF. This attribute is used for Transmitted PT";
        }
        leaf exp-pt {
          yang:get-supported "true";
          type ciena-6500-types:STRING;
          description
            "HEX value in the range 0x00-0xFF. This attribute is used for Expected PT";
        }
        leaf received-upi {
          yang:get-supported "true";
          type ciena-6500-types:STRING;
          description
            "HEX value in the range 0x00-0xFF. This attribute is used for Received UPI";
        }
        leaf tx-upi {
          yang:get-supported "true";
          type ciena-6500-types:STRING;
          description
            "HEX value in the range 0x00-0xFF. This attribute is used for Transmitted UPI";
        }
        leaf expected-upi {
          yang:get-supported "true";
          type ciena-6500-types:STRING;
          description
            "HEX value in the range 0x00-0xFF. This attribute is used for Expected UPI";
        }
        leaf rx-cos-profile {
          yang:get-supported "true";
          type ciena-6500-types:STRING;
          description
            "The AID of the port RX COS Profile (RXCOSPRF-shelf-profileNo)";
        }
        leaf tx-cos-profile {
          yang:get-supported "true";
          type ciena-6500-types:STRING;
          description
            "The AID of the port TX COS Profile (TXCOSPRF-shelf-profileNo)";
        }
        leaf user-rx-cos {
          yang:get-supported "true";
          type ciena-6500-types:INT {
            range "0..15";
          }
          description
            "The IPHB value to map the untagged frames";
        }
        leaf q-grp-1 {
          yang:get-supported "true";
          type ciena-6500-types:STRING;
          description
            "The AID of the queue group profile (QGRP-shelf-profileNo) to be used for queue group 1.";
        }
        leaf q-grp-2 {
          yang:get-supported "true";
          type ciena-6500-types:STRING;
          description
            "The AID of the queue group profile (QGRP-shelf-profileNo) to be used for queue group 2.";
        }
        leaf wan-cap {
          yang:get-supported "true";
          type enumeration {
            enum HICAP {
              description
                "WAN port supports rate up to STS-192";
            }
            enum MEDCAP {
              description
                "WAN port supports rate up to STS-24";
            }
            enum LOCAP {
              description
                "WAN port supports rate up to STS-3";
            }
          }
          description
            "This attribute indicates the capacity of the WAN port";
        }
        leaf pbt-list-sup {
          yang:get-supported "true";
          type ciena-6500-types:INT {
            range "0 | 1";
          }
          description
            "Indicates the PBT VID list support on WAN facility";
        }
        leaf pdh-vli {
          yang:get-supported "true";
          type enumeration {
            enum DISABLE {
              description
                "Default - VLI overhead octet used for data";
            }
            enum ENABLE {
              description
                "VLI overhead octet set to zeros.";
            }
          }
          description
            "This attribute is used to specify VLI octet usage for PDH WANs. VLI=Vcat Lcas Interworking, the concatenation overhead octet.";
        }
        leaf mac-option {
          yang:get-supported "true";
          type enumeration {
            enum NONE {
              description
                "No MAC provisioned on the facility.";
            }
            enum MANUAL {
              description
                "MAC manually provisioned on the facility.";
            }
            enum AUTO {
              description
                "MAC automatically assigned to the facility.";
            }
          }
          description
            "The MAC provisioning option";
        }
        leaf mac {
          yang:get-supported "true";
          type ciena-6500-types:IDENT;
          description
            "48-bit Ethernet MAC address displayed as 12 alphanumeric characters. Unique to each facility.";
        }
        leaf os-tran {
          yang:get-supported "true";
          type enumeration {
            enum NONE {
              description
                "This value is used when OSTRAN is not applicable.";
            }
            enum LEGACYCMF {
              description
                "Proprietary Legacy Client Managed Frame.";
            }
            enum G7041CMF {
              description
                "G704.1 standard GFP Client Managed Frame.";
            }
            enum G7041CDF {
              description
                "Ordered Set Transparency encapsulated in Client Data Frame.";
            }
          }
          description
            "This attribute is used to specify whether the WAN facility supports Ordered Set Transparency for G704.1 compliance.";
        }
        leaf supported-term-pt {
          yang:get-supported "true";
          type ciena-6500-types:STRING;
          description
            "Facility AID format. The supporting Termination Point.";
        }
        leaf direction {
          yang:get-supported "true";
          type enumeration {
            enum RX {
              description
                "Monitoring receive direction";
            }
            enum TX {
              description
                "Monitoring transmit direction";
            }
          }
          description
            "Monitoring GFP layer in receive or transmit direction";
        }
        leaf reserved {
          yang:get-supported "true";
          type ciena-6500-enums:BOOL_YES_NO;
          description
            "Specify if the facility is being reserved for packet SNC's";
        }
        leaf rxmon {
          yang:get-supported "true";
          type ciena-6500-enums:BOOL_YES_NO_defaultNO;
          description
            "Indicate if the signal is monitored in the Rx direction for alarms and PMs and OMs.";
        }
        leaf rxterm {
          yang:get-supported "true";
          type ciena-6500-enums:BOOL_YES_NO_defaultNO;
          description
            "Indicate if the signal is terminated in the Rx direction or not.";
        }
        leaf tx-mon {
          yang:get-supported "true";
          type ciena-6500-enums:BOOL_YES_NO_defaultNO;
          description
            "Indicate if the signal is monitored in the Tx direction for alarms and PMs and OMs.";
        }
        leaf tx-term {
          yang:get-supported "true";
          type ciena-6500-enums:BOOL_YES_NO_defaultNO;
          description
            "Indicate if the signal is terminated in the Tx direction for alarms and PMs and OMs.";
        }
        leaf pst {
          yang:get-supported "true";
          type enumeration {
            enum IS {
              description
                "In Service";
            }
            enum IS-ANR {
              description
                "In Service - Abnormal";
            }
            enum OOS-MA {
              description
                "Out-of-service maintenance for provisioning memory administration";
            }
            enum OOS-AU {
              description
                "Out-of-service autonomous from a failure detected point of view. It is not out of service from a state point of view. Alarm is raised if the entity is not able to perform its provisioned functions";
            }
            enum OOS-AUMA {
              description
                "Out-of-service autonomous management - the entity is not able to perform its provisioned functions and is purposefully removed from service";
            }
            enum OOS-MAANR {
              description
                "Out-of-service maintenance - abnormal.";
            }
          }
          description
            "Identify the primary state";
        }
        leaf-list sst {
          yang:get-supported "true";
          type enumeration {
            enum AINS {
              description
                "Auto-In-Service";
            }
            enum AINS-DEA {
              description
                "Auto-In-Service-Deactivate";
            }
            enum MT {
              description
                "Maintenance";
            }
            enum ACT {
              description
                "Active, carrying traffic";
            }
            enum DISCD {
              description
                "Idle, not carrying traffic";
            }
            enum FLT {
              description
                "Fault detected in equipment";
            }
            enum SGEO {
              description
                "Supporting entity outage";
            }
            enum WRKRX {
              description
                "Working in the receive direction";
            }
            enum WRKTX {
              description
                "Working in the transmit direction";
            }
            enum UEQ {
              description
                "Unequipped";
            }
            enum MEA {
              description
                "Mismatched equipment attributes";
            }
            enum DSBLD {
              description
                "Missing layer 2 connection; Idle, not carrying traffic";
            }
            enum UAS {
              description
                "RPR WAN only, Not associated to an RPR SPAN";
            }
          }
          description
            "Identify the secondary state";
        }
      }
    }
  }

  rpc port-enable-eth10g {
    description
      "Restore Ethernet10G Facility: This command allows you to restore a facility to service. The facility goes from a maintenance state to an in-service state.";
    yang:handler "tl1";
    input {
      leaf eth10g {
        mandatory true;
        description
          "AID in format ETH10G-shelf-slot-port, ETH10G-shelf-slot-portSsubport";
        type ciena-6500-types:aid;
      }
    }
  }

  rpc port-disable-eth10g {
    description
      "Remove Ethernet10G Facility: This command allows you to remove the specified facility from service and put it in an out-of-service for maintenance state.";
    yang:handler "tl1";
    input {
      leaf eth10g {
        mandatory true;
        description
          "AID in format ETH10G-shelf-slot-port, ETH10G-shelf-slot-portSsubport";
        type ciena-6500-types:aid;
      }
      leaf sst {
        type ciena-6500-enums:RMVSSTMT;
        description
          "Identify Maintenance State";
      }
    }
  }

  rpc port-show-eth10g {
    description
      "Retrieve Ethernet10G Facility: Retrieve Ethernet Facility attributes.";
    yang:handler "tl1";
    input {
      leaf eth10g {
        mandatory true;
        description
          "AID in format ETH10G-shelf-slot-port, ETH10G-shelf-slot-portSsubport";
        type ciena-6500-types:aid;
      }
      leaf stats-info {
        yang:get-supported "true";
        type enumeration {
          enum NO {
            description
              "Do not include Dynamic Status information in the response";
          }
          enum YES {
            description
              "Include Dynamic Status information in the response";
          }
        }
        description
          "Specify if Dynamic Status Information is to be included in the response.";
      }
    }
    output {
      list output {
        leaf eth10g {
          yang:get-supported "true";
          type ciena-6500-types:IDENT;
          description
            "aid";
        }
        leaf laser-off-far-end-fail {
          yang:get-supported "true";
          type ciena-6500-enums:Laserofffarendfail;
          description
            "Enable or Disable LOL (Loss of Light) feature";
        }
        leaf tx-act-pwr {
          yang:get-supported "true";
          type ciena-6500-types:STRING;
          description
            "TX actual power in dBm (xx.x)";
        }
        leaf tx-min-pwr {
          yang:get-supported "true";
          type ciena-6500-types:STRING;
          description
            "TX minimum power in dBm (xx.x)";
        }
        leaf tx-max-pwr {
          yang:get-supported "true";
          type ciena-6500-types:STRING;
          description
            "TX maximum power in dBm (xx.x)";
        }
        leaf rx-act-pwr {
          yang:get-supported "true";
          type ciena-6500-types:STRING;
          description
            "RX actual power in dBm (xx.x)";
        }
        leaf rx-min-pwr {
          yang:get-supported "true";
          type ciena-6500-types:STRING;
          description
            "RX minimum power in dBm (xx.x)";
        }
        leaf rx-max-pwr {
          yang:get-supported "true";
          type ciena-6500-types:STRING;
          description
            "RX maximum power in dBm (xx.x)";
        }
        leaf mtu {
          yang:get-supported "true";
          type ciena-6500-enums:MTU;
          description
            "Maximum Ethernet frame size supported. Setting the MTU size will influence the distance lossless local flow control is supported (the smaller the MTU, the larger the lossless distance).";
        }
        leaf flow-ctrl {
          yang:get-supported "true";
          type ciena-6500-enums:FLOWCTRL;
          description
            "Advertised flow control capabilities.";
        }
        leaf auto-neg {
          yang:get-supported "true";
          type enumeration {
            enum ENABLE;
            enum DISABLE {
              description
                "Always Disable for 10GE.";
            }
          }
          description
            "Auto-negotiation, R/W, only one value supported=DISABLE on 10GE.";
        }
        leaf an-status {
          yang:get-supported "true";
          type enumeration {
            enum INPROGRESS;
            enum COMPLETED;
            enum DISABLED;
            enum UNKNOWN {
              description
                "Always UNKNOWN for 10GE.";
            }
          }
          description
            "Auto-negotiation status";
        }
        leaf eth-duplex {
          yang:get-supported "true";
          type enumeration {
            enum FULL {
              description
                "Always FULL for 10GE";
            }
            enum HALF;
            enum BOTH;
          }
          description
            "Advertised duplex operation capabilities if AN is enabled.";
        }
        leaf speed {
          yang:get-supported "true";
          type enumeration {
            enum 10G {
              description
                "Always 10G for 10GE";
            }
          }
          description
            "Only one value is allowed, Always 10G.";
        }
        leaf tx-con {
          yang:get-supported "true";
          type enumeration {
            enum ENABLE;
            enum DISABLE;
          }
          description
            "Control the EPL conditioning. Enabling will turn off the GigE laser when Ethernet conditioning is required. Disabling will prevent Ethernet conditioning (i.e. the GigE laser will remain enabled) as a result of SONET/SDH path failure, as well as GFP failures and GFP RFI/CSF client management frame reception.";
        }
        leaf tx-inter-pkt-gap {
          yang:get-supported "true";
          type enumeration {
            enum 11;
            enum 12;
          }
          description
            "Tx Inter-Packet Gap. 12 is the default value.";
        }
        leaf tx-con-hb {
          yang:get-supported "true";
          type enumeration {
            enum DISABLE;
            enum ENABLE;
            enum TXONLY;
          }
          description
            "Used to control conditioning of client ports through Heartbeat mechanism with remote using Y.1731 CCM PDUs.";
        }
        leaf tx-con-hb-interval {
          yang:get-supported "true";
          type enumeration {
            enum 100MSEC;
            enum 1SEC;
          }
          description
            "Tx Conditioning Heartbeat Interval";
        }
        leaf tx-con-md-level {
          default "0";
          yang:get-supported "true";
          type ciena-6500-types:INT {
            range "0..7";
          }
          description
            "Tx Conditioning MD Level";
        }
        leaf tx-cond-network-flt-sig {
          yang:get-supported "true";
          type enumeration {
            enum TLV;
            enum EXPLICIT;
            enum CFM;
          }
          description
            "Tx Conditioning Network Fault Signal";
        }
        leaf pause-tx {
          yang:get-supported "true";
          type enumeration {
            enum ENABLE;
            enum DISABLE;
          }
          description
            "Controls PAUSE transmission when AN is disabled. Ignored when AN is enabled.";
        }
        leaf pause-rx {
          yang:get-supported "true";
          type enumeration {
            enum ENABLE;
            enum DISABLE {
              description
                "Always DISABLE for 10GE";
            }
          }
          description
            "Controls PAUSE reception when AN is disabled. Ignored when AN is enabled.";
        }
        leaf pause-rx-override {
          yang:get-supported "true";
          type enumeration {
            enum ENABLE;
            enum DISABLE;
          }
          description
            "If AN is enabled, and ANPAUSERX is negotiated to enable, setting this attribute to enable means received PAUSE frames will not be acted upon. They will either be discarded or pass through transparently (based on the PASSCTRL setting).";
        }
        leaf pause-tx-override {
          yang:get-supported "true";
          type enumeration {
            enum ENABLE;
            enum DISABLE {
              description
                "Always DISABLE for 10GE";
            }
          }
          description
            "Controls PAUSE reception when AN is disabled. Ignored when AN is enabled.";
        }
        leaf an-eth-duplex {
          yang:get-supported "true";
          type enumeration {
            enum FULL;
            enum HALF;
            enum BOTH;
            enum UNKNOWN {
              description
                "Always UNKNOWN for 10GE";
            }
          }
          description
            "Negotiated Duplex Operation, when AN is enabled.";
        }
        leaf an-speed {
          yang:get-supported "true";
          type enumeration {
            enum 10G;
            enum UNKNOWN {
              description
                "Always UNKNOWN for 10GE.";
            }
          }
          description
            "Negotiated speed, when AN is enabled.";
        }
        leaf an-pause-tx {
          yang:get-supported "true";
          type enumeration {
            enum ENABLE;
            enum DISABLE;
            enum UNKNOWN {
              description
                "Always UNKNOWN for 10GE.";
            }
          }
          description
            "Negotiated PAUSE transmit, when AN is enabled.";
        }
        leaf an-pause-rx {
          yang:get-supported "true";
          type enumeration {
            enum ENABLE;
            enum DISABLE;
            enum UNKNOWN {
              description
                "Always UNKNOWN for 10GE.";
            }
          }
          description
            "Negotiated PAUSE receive, when AN is enabled.";
        }
        leaf adv-eth-duplex {
          yang:get-supported "true";
          type enumeration {
            enum FULL;
            enum HALF;
            enum BOTH;
            enum UNKNOWN {
              description
                "Always UNKNOWN for 10GE.";
            }
          }
          description
            "Link partner advertised Duplex capabilities. Only valid when ANSTATUS is COMPLETED.";
        }
        leaf adv-speed {
          yang:get-supported "true";
          type enumeration {
            enum 10G;
            enum UNKNOWN {
              description
                "Always UNKNOWN for 10GE.";
            }
          }
          description
            "Link partner advertised speed capabilities. Only valid when ANSTATUS is COMPLETED.";
        }
        leaf adv-flow-ctrl {
          yang:get-supported "true";
          type enumeration {
            enum NONE;
            enum ASYM;
            enum SYM;
            enum UNKNOWN {
              description
                "Always UNKNOWN for 10GE";
            }
          }
          description
            "Link partner advertised flow control capabilities. Only valid when ANSTATUS is COMPLETED.";
        }
        leaf pass-ctrl {
          yang:get-supported "true";
          type enumeration {
            enum ENABLE;
            enum DISABLE {
              description
                "Always DISABLE for 10GE.";
            }
          }
          description
            "Controls whether transmitted Ethernet Control Frames (T/L=8808) are passed transparently (Enable), or removed from the flow (Disable).";
        }
        leaf phys-addr {
          yang:get-supported "true";
          type ciena-6500-types:IDENT;
          description
            "48-bit Ethernet MAC address displayed as 12 alphanumeric characters. Used as SA in PAUSE frames.";
        }
        leaf eqpt {
          yang:get-supported "true";
          type enumeration {
            enum XGELAN;
            enum XGEWAN;
          }
          description
            "Interface equipment type.";
        }
        leaf rx-idle {
          yang:get-supported "true";
          type enumeration {
            enum 0;
            enum 1;
            enum 2;
            enum 3;
            enum 4;
            enum 5;
            enum 10;
            enum 60;
            enum 120;
            enum 300;
          }
          description
            "Always 0 for 10GE.";
        }
        leaf if-type {
          yang:get-supported "true";
          type enumeration {
            enum UNI;
            enum NNI;
          }
          description
            "The type of the ETH10G facility being queried";
        }
        leaf policing {
          yang:get-supported "true";
          type enumeration {
            enum ENABLE;
            enum DISABLE;
          }
          description
            "Indicates whether policing will be done on the given port";
        }
        leaf e-type {
          yang:get-supported "true";
          type string {
            length "1..4";
          }
          description
            "Encapsulation scheme used in customer frames";
        }
        leaf latency-opt {
          yang:get-supported "true";
          type enumeration {
            enum MINIMUM;
            enum MEDIUM;
            enum MAXIMUM;
          }
          description
            "Latency Optimization";
        }
        leaf sync-status-msg-transmit {
          yang:get-supported "true";
          type ciena-6500-enums:SSMTRANSMIT;
          description
            "Synchronized Status Messaging Transmit.";
        }
        leaf dus-override {
          yang:get-supported "true";
          type enumeration {
            enum ENABLE;
            enum DISABLE;
          }
          description
            "A parameter which allows the synchronization quality level of a line reference to be overriden even when the receiving quality level is DUS.";
        }
        leaf cbr-bw-remain {
          yang:get-supported "true";
          type ciena-6500-types:STRING;
          description
            "CBR Bandwidth Remain";
        }
        leaf dm-prf {
          yang:get-supported "true";
          type ciena-6500-types:STRING;
          description
            "(DEPRECATED) Discard Marking Profile";
        }
        leaf cf-prf {
          yang:get-supported "true";
          type ciena-6500-types:STRING;
          description
            "The AID of the port Control Frame Profile (CFPRF-shelf-profileNo)";
        }
        leaf sch-prf {
          yang:get-supported "true";
          type ciena-6500-types:STRING;
          description
            "(DEPRECATED) Scheduler Profiler";
        }
        leaf lag-id {
          yang:get-supported "true";
          type ciena-6500-types:STRING;
          description
            "The AID of the LAG to which the given ETH10G port belongs.";
        }
        leaf rx-cos-profile {
          yang:get-supported "true";
          type ciena-6500-types:STRING;
          description
            "The AID of the port RX COS Profile (RXCOSPRF-shelf-profileNo)";
        }
        leaf tx-cos-profile {
          yang:get-supported "true";
          type ciena-6500-types:STRING;
          description
            "The AID of the port TX COS Profile (TXCOSPRF-shelf-profileNo)";
        }
        leaf user-rx-cos {
          yang:get-supported "true";
          type ciena-6500-types:INT {
            range "0..15";
          }
          description
            "The IPHB value to map the untagged frames";
        }
        leaf q-grp-1 {
          yang:get-supported "true";
          type ciena-6500-types:STRING;
          description
            "The AID of the queue group profile (QGRP-shelf-profileNo) to be used for queue group 1.";
        }
        leaf q-grp-2 {
          yang:get-supported "true";
          type ciena-6500-types:STRING;
          description
            "The AID of the queue group profile (QGRP-shelf-profileNo) to be used for queue group 2.";
        }
        leaf port-bw {
          yang:get-supported "true";
          type ciena-6500-types:STRING;
          description
            "The AID of the bandwidth profile (BWPRF-shelf-profileNo).";
        }
        leaf pbt-list-sup {
          yang:get-supported "true";
          type ciena-6500-types:INT {
            range "0 | 1";
          }
          description
            "Indicates the PBT VID list support on Ethernet facility";
        }
        leaf mapping {
          yang:get-supported "true";
          type enumeration {
            enum PROP237 {
              description
                "proportional 11.09";
            }
            enum PROP238 {
              description
                "proportional 11.05";
            }
            enum GFPMACTR {
              description
                "GFP-F mapped, MAC transparent";
            }
            enum GFPSTD {
              description
                "GFP-F mapped, Standard WAN";
            }
            enum GFPMACTR192 {
              description
                "GFP-F mapped, MAC transparent, port mode of layer facility is SONET";
            }
            enum GFPSTD192 {
              description
                "GFP-F mapped, Standard WAN, port mode of layer facility is SONET";
            }
            enum GFPMACTR64 {
              description
                "GFP-F mapped, MAC transparent, port mode of layer facility is SDH";
            }
            enum GFPSTD64 {
              description
                "GFP-F mapped, Standard WAN, port mode of layer facility is SDH";
            }
            enum GFPMACOSTR {
              description
                "GFP-F mapped, Ordered Set MAC transparent";
            }
            enum GFPMACOSTR192 {
              description
                "GFP-F mapped, Ordered Set MAC transparent, port mode of layer facility is SONET";
            }
            enum GFPMACOSTR64 {
              description
                "GFP-F mapped, Ordered Set MAC transparent, port mode of layer facility is SDH";
            }
            enum NONE {
              description
                "Not mapped";
            }
            enum ULL {
              description
                "Ultra Low Latency";
            }
          }
          description
            "The mapping layer OTM2 OTURATE and client mapping";
        }
        leaf timing-ref {
          yang:get-supported "true";
          type enumeration {
            enum N {
              description
                "Not a timing reference";
            }
            enum Y {
              description
                "Is a timing reference";
            }
          }
          description
            "Indicates whether the ETH10G facility is a timing reference";
        }
        leaf rate {
          yang:get-supported "true";
          type ciena-6500-types:INT {
            range "10 | 20 | 30..10000";
          }
          description
            "The EVPL bandwidth rate.";
        }
        leaf mode {
          yang:get-supported "true";
          type enumeration {
            enum L2;
            enum EVPL;
          }
          description
            "The mode of service.";
        }
        leaf ains-time-left {
          yang:get-supported "true";
          type ciena-6500-types:TIME;
          description
            "The format will be HH-MM for the time left in AINS timeout.";
        }
        leaf clfi {
          yang:get-supported "true";
          type ciena-6500-types:STRING;
          description
            "Common Language Facility Identifier.Customer provisionable label for a facility.";
        }
        leaf hold-off {
          yang:get-supported "true";
          type ciena-6500-types:INT {
            range "0 | 100 | 200 | 300 | 400 | 500 | 600 | 700 | 800 | 900 | 1000";
          }
          description
            "Conditioning holdoff time in milliseconds.";
        }
        leaf tx-wvlngth-prov {
          yang:get-supported "true";
          type ciena-6500-types:STRING;
          description
            "Provisioned Wavelength in nm (xxxx.xx)";
        }
        leaf tx-wvlngth-min {
          default "0.00";
          yang:get-supported "true";
          type ciena-6500-types:STRING;
          description
            "Minimum Wavelength value in nm (xxxx.xx)";
        }
        leaf tx-wvlngth-max {
          default "0.00";
          yang:get-supported "true";
          type ciena-6500-types:STRING;
          description
            "Maximum Wavelength value in nm (xxxx.xx)";
        }
        leaf tx-wvlngth-spacing {
          yang:get-supported "true";
          type ciena-6500-types:STRING;
          description
            "OCH Wavelength Spacing in Ghz";
        }
        leaf spli-mgmt {
          yang:get-supported "true";
          type ciena-6500-enums:spliMgmt;
          description
            "Identify if Port is Manageable by SPLI";
        }
        leaf spli-managed {
          yang:get-supported "true";
          type ciena-6500-enums:spliManaged;
          description
            "Identify if Port is Currently Managed by SPLI";
        }
        leaf lldpmon {
          yang:get-supported "true";
          type ciena-6500-enums:LLDPMON_REFID;
          description
            "Specifies if facility is monitoring LLDP packets or not.";
        }
        leaf pst {
          yang:get-supported "true";
          type enumeration {
            enum IS {
              description
                "In Service";
            }
            enum IS-ANR {
              description
                "In Service - Abnormal";
            }
            enum OOS-MA {
              description
                "Out-of-service maintenance for provisioning memory administration";
            }
            enum OOS-AU {
              description
                "Out-of-service autonomous from a failure detected point of view. It is not out of service from a state point of view. Alarm is raised if the entity is not able to perform its provisioned functions";
            }
            enum OOS-AUMA {
              description
                "Out-of-service autonomous management - the entity is not able to perform its provisioned functions and is purposefully removed from service";
            }
            enum OOS-MAANR {
              description
                "Out-of-service maintenance - abnormal";
            }
          }
          description
            "Identify the primary state";
        }
        leaf-list sst {
          yang:get-supported "true";
          type enumeration {
            enum AINS {
              description
                "Auto-In-Service";
            }
            enum MT {
              description
                "Maintenance";
            }
            enum FLT {
              description
                "Fault detected in equipment";
            }
            enum LPBK {
              description
                "Loopback";
            }
            enum SGEO {
              description
                "Supporting entity outage";
            }
            enum DISCD {
              description
                "Disconnected. (no transparent traffic connection on this facility)";
            }
            enum TSGEN {
              description
                "Test set generation";
            }
            enum TSMON {
              description
                "Test set monitor";
            }
          }
          description
            "Identify the secondary state";
        }
      }
    }
  }

  rpc port-enable-ethn {
    description
      "RST-ETHN Switch ETHn Facility In Service";
    yang:handler "tl1";
    input {
      leaf ethn {
        mandatory true;
        description
          "AID in format ETH100G-shelf-slot-port, ETH40G-shelf-slot-port";
        type ciena-6500-types:aid;
      }
    }
  }

  rpc port-disable-ethn {
    description
      "Remove Switch ETHn Facility Out of Service";
    yang:handler "tl1";
    input {
      leaf ethn {
        mandatory true;
        description
          "AID in format ETH100G-shelf-slot-port, ETH40G-shelf-slot-port";
        type ciena-6500-types:aid;
      }
      leaf sst {
        type ciena-6500-enums:RMVSSTMT;
        description
          "Identify Maintenance State";
      }
    }
  }

  rpc port-show-ethn {
    description
      "RTRV-ETHN Retrieve Provisioned ETHn Facilities";
    yang:handler "tl1";
    input {
      leaf ethn {
        mandatory true;
        description
          "AID in format ETH100G-shelf-slot-port, ETH40G-shelf-slot-port";
        type ciena-6500-types:aid;
      }
      leaf stats-info {
        yang:get-supported "true";
        type enumeration {
          enum NO {
            description
              "Do not include Dynamic Status information in the response";
          }
          enum YES {
            description
              "Include Dynamic Status information in the response";
          }
        }
        description
          "Specify if Dynamic Status Information is to be included in the response";
      }
    }
    output {
      list output {
        leaf ethn {
          yang:get-supported "true";
          type ciena-6500-types:IDENT;
          description
            "aid";
        }
        leaf laser-off-far-end-fail {
          yang:get-supported "true";
          type ciena-6500-enums:Laserofffarendfail;
          description
            "Enable the feature of laser off far end fail";
        }
        leaf mapping {
          yang:get-supported "true";
          type enumeration {
            enum GMP {
              description
                "GMP";
            }
            enum GFPFLEX {
              description
                "GFPFLEX mapping";
            }
          }
          description
            "Mapping";
        }
        leaf-list tx-act-ln-pwr {
          yang:get-supported "true";
          type ciena-6500-types:STRING;
          description
            "Lanes TX Power(Format:Lane1|Lane2|...)";
        }
        leaf tx-act-high-pwr {
          yang:get-supported "true";
          type ciena-6500-types:STRING;
          description
            "TX Actual High Power Value in dBm (xx.x)";
        }
        leaf tx-act-low-pwr {
          yang:get-supported "true";
          type ciena-6500-types:STRING;
          description
            "TX Actual Low Power Value in dBm (xx.x)";
        }
        leaf tx-min-pwr {
          yang:get-supported "true";
          type ciena-6500-types:STRING;
          description
            "TX minimum power in dBm (xx.x)";
        }
        leaf tx-max-pwr {
          yang:get-supported "true";
          type ciena-6500-types:STRING;
          description
            "TX maximum power in dBm (xx.x)";
        }
        leaf-list rx-act-ln-pwr {
          yang:get-supported "true";
          type ciena-6500-types:STRING;
          description
            "Lanes RX Power(Format:Lane1|Lane2|...)";
        }
        leaf rx-act-high-pwr {
          yang:get-supported "true";
          type ciena-6500-types:STRING;
          description
            "RX Actual High Power Value in dBm (xx.x)";
        }
        leaf rx-act-low-pwr {
          yang:get-supported "true";
          type ciena-6500-types:STRING;
          description
            "RX Actual Low Power Value in dBm (xx.x)";
        }
        leaf rx-min-pwr {
          yang:get-supported "true";
          type ciena-6500-types:STRING;
          description
            "RX minimum power in dBm (xx.x)";
        }
        leaf rx-max-pwr {
          yang:get-supported "true";
          type ciena-6500-types:STRING;
          description
            "RX maximum power in dBm (xx.x)";
        }
        leaf ains-time-left {
          yang:get-supported "true";
          type ciena-6500-types:TIME;
          description
            "The format will be HH-MM for the time left in AINS timeout.";
        }
        leaf clfi {
          yang:get-supported "true";
          type ciena-6500-types:STRING;
          description
            "Common Language Facility Identifier.Customer provisionable label for a facility.";
        }
        leaf mtu {
          yang:get-supported "true";
          type ciena-6500-enums:MTU;
          description
            "Maximum Ethernet frame size supported. Setting the MTU size will influence the distance lossless local flow control is supported (the smaller the MTU, the larger the lossless distance).";
        }
        leaf member-1 {
          yang:get-supported "true";
          type ciena-6500-types:STRING;
          description
            "The AID of member 1 (FLEX-shelf-slot-port).";
        }
        leaf member-2 {
          yang:get-supported "true";
          type ciena-6500-types:STRING;
          description
            "The AID of member 2 (FLEX-shelf-slot-port).";
        }
        leaf member-3 {
          yang:get-supported "true";
          type ciena-6500-types:STRING;
          description
            "The AID of member 3 (FLEX-shelf-slot-port).";
        }
        leaf member-4 {
          yang:get-supported "true";
          type ciena-6500-types:STRING;
          description
            "The AID of member 4 (FLEX-shelf-slot-port).";
        }
        leaf fec-frmt {
          yang:get-supported "true";
          type enumeration {
            enum OFF {
              description
                "NO FEC";
            }
            enum RS10 {
              description
                "RS10 FEC";
            }
          }
          description
            "FEC Format";
        }
        leaf pre-fec-sf-th-lev {
          yang:get-supported "true";
          type decimal64 {
            range "-1.00..1.00";
            fraction-digits 2;
          }
          description
            "Pre-FEC Signal Fail Threshold Level (in dBQ).";
        }
        leaf pre-fec-sf-th-ber {
          yang:get-supported "true";
          type ciena-6500-types:STRING;
          description
            "Pre-FEC Signal Fail Threshold Bit Error Rate.";
        }
        leaf pre-fec-sd-th-lev {
          yang:get-supported "true";
          type decimal64 {
            range "-1.00..2.00";
            fraction-digits 2;
          }
          description
            "Pre-FEC Signal Degrade Threshold Level (in dBQ).";
        }
        leaf pre-fec-sd-th-ber {
          yang:get-supported "true";
          type ciena-6500-types:STRING;
          description
            "Pre-FEC Signal Degrade Threshold Bit Error Rate.";
        }
        leaf spli-mgmt {
          yang:get-supported "true";
          type ciena-6500-enums:spliMgmt;
          description
            "Identify if Port is Manageable by SPLI";
        }
        leaf spli-managed {
          yang:get-supported "true";
          type ciena-6500-enums:spliManaged;
          description
            "Identify if Port is Currently Managed by SPLI";
        }
        leaf hold-off {
          yang:get-supported "true";
          type ciena-6500-types:INT {
            range "0 | 100 | 200 | 300 | 400 | 500 | 600 | 700 | 800 | 900 | 1000";
          }
          description
            "Hold Off signal conditioning timer (in increments of 100).";
        }
        leaf lldpmon {
          yang:get-supported "true";
          type ciena-6500-enums:LLDPMON_REFID;
          description
            "Specifies if facility is monitoring LLDP packets or not.";
        }
        leaf pst {
          yang:get-supported "true";
          type enumeration {
            enum IS {
              description
                "In Service";
            }
            enum IS-ANR {
              description
                "In Service - Abnormal";
            }
            enum OOS-MA {
              description
                "Out-of-service maintenance for provisioning memory administration";
            }
            enum OOS-AU {
              description
                "Out-of-service autonomous from a failure detected point of view. It is not out of service from a state point of view. Alarm is raised if the entity is not able to perform its provisioned functions";
            }
            enum OOS-AUMA {
              description
                "Out-of-service autonomous management - the entity is not able to perform its provisioned functions and is purposefully removed from service";
            }
            enum OOS-MAANR {
              description
                "Out-of-service maintenance - abnormal";
            }
          }
          description
            "Identify the primary state";
        }
        leaf-list sst {
          yang:get-supported "true";
          type enumeration {
            enum AINS {
              description
                "Auto-In-Service";
            }
            enum MT {
              description
                "Maintenance";
            }
            enum FLT {
              description
                "Fault detected in equipment";
            }
            enum LPBK {
              description
                "Loopback";
            }
            enum SGEO {
              description
                "Supporting entity outage";
            }
            enum DISCD {
              description
                "Disconnected (no transparent traffic connection on this facility)";
            }
            enum TSGEN {
              description
                "Test set generation";
            }
            enum TSMON {
              description
                "Test set monitor";
            }
          }
          description
            "Identify the secondary state";
        }
      }
    }
  }

  rpc port-show-flex {
    description
      "Retrieve Flex Facility: Retrieve FLEX Facility attributes.";
    yang:handler "tl1";
    input {
      leaf flex {
        mandatory true;
        description
          "AID in format FLEX-shelf-slot-port, FLEX-shelf-slot-portSsubport";
        type ciena-6500-types:aid;
      }
      leaf stats-info {
        yang:get-supported "true";
        type enumeration {
          enum NO;
          enum YES;
        }
        description
          "Include Dynamic Status Information in the Response";
      }
      leaf trc-info {
        yang:get-supported "true";
        type enumeration {
          enum NO;
          enum YES;
        }
        description
          "Include Trace Information in the Response";
      }
    }
    output {
      list output {
        leaf flex {
          yang:get-supported "true";
          type ciena-6500-types:IDENT;
          description
            "aid";
        }
        leaf protocol {
          yang:get-supported "true";
          type ciena-6500-enums:PROTOCOL;
          description
            "Protocol";
        }
        leaf rate {
          yang:get-supported "true";
          type ciena-6500-types:STRING;
          description
            "Protocol Rate, in Mbps. Supported values are 1000, 1062.5, 1250, 2125, 4250, 8500, and 10500.";
        }
        leaf mapping {
          yang:get-supported "true";
          type ciena-6500-enums:FLEX_MAPPING;
          description
            "Mapping type";
        }
        leaf latency-opt {
          yang:get-supported "true";
          type enumeration {
            enum MINIMUM;
            enum MEDIUM;
            enum MAXIMUM;
          }
          description
            "Latency Optimization";
        }
        leaf tx-con {
          yang:get-supported "true";
          type enumeration {
            enum LOFEF {
              description
                "Laser Off Far End Fail";
            }
            enum 8B10B {
              description
                "8B10B";
            }
            enum NOS {
              description
                "NOS";
            }
            enum K30_7 {
              description
                "K30_7";
            }
            enum LF {
              description
                "Local Fault";
            }
            enum LNKFLTC1C2 {
              description
                "LNKFLTC1C2";
            }
          }
          description
            "TX conditioning";
        }
        leaf hold-off {
          yang:get-supported "true";
          type ciena-6500-types:INT {
            range "0 | 100 | 200..2000";
          }
          description
            "Conditioning holdoff time in seconds.";
        }
        leaf tf-mode {
          yang:get-supported "true";
          type enumeration {
            enum OFF {
              description
                "Alarms off, no traffic protection";
            }
            enum ALMONLY {
              description
                "Alarms on, no traffic protection";
            }
            enum LINEFAIL {
              description
                "Alarms on, with traffic protection";
            }
          }
          description
            "Trace Fail Mode";
        }
        leaf mappedrate {
          yang:get-supported "true";
          type ciena-6500-types:INT;
          description
            "Mapped Rate, in Mbps";
        }
        leaf trc {
          yang:get-supported "true";
          type string {
            length "1..48";
          }
          description
            "Outgoing Trace Message";
        }
        leaf exp-trc {
          yang:get-supported "true";
          type string {
            length "1..48";
          }
          description
            "Expected Trace Message";
        }
        leaf defrag-hit {
          yang:get-supported "true";
          type enumeration {
            enum YES {
              description
                "Traffic is impacted on this port";
            }
            enum NO {
              description
                "No Traffic impact on this port";
            }
          }
          description
            "Determine if this port will be impacted by Bandwidth Defragmenation";
        }
        leaf tx-act-pwr {
          yang:get-supported "true";
          type ciena-6500-types:STRING;
          description
            "TX actual power in dBm (xx.x)";
        }
        leaf tx-min-pwr {
          yang:get-supported "true";
          type ciena-6500-types:STRING;
          description
            "TX minimum power in dBm (xx.x)";
        }
        leaf tx-max-pwr {
          yang:get-supported "true";
          type ciena-6500-types:STRING;
          description
            "TX maximum power in dBm (xx.x)";
        }
        leaf rx-act-pwr {
          yang:get-supported "true";
          type ciena-6500-types:STRING;
          description
            "RX actual power in dBm (xx.x)";
        }
        leaf rx-min-pwr {
          yang:get-supported "true";
          type ciena-6500-types:STRING;
          description
            "RX minimum power in dBm (xx.x)";
        }
        leaf rx-max-pwr {
          yang:get-supported "true";
          type ciena-6500-types:STRING;
          description
            "RX maximum power in dBm (xx.x)";
        }
        leaf ains-time-left {
          yang:get-supported "true";
          type ciena-6500-types:TIME;
          description
            "The format will be HH-MM for the time left in AINS timeout.";
        }
        leaf clfi {
          yang:get-supported "true";
          type ciena-6500-types:STRING;
          description
            "Common Language Facility Identifier.Customer provisionable label for a facility.";
        }
        leaf prime {
          yang:get-supported "true";
          type ciena-6500-types:STRING;
          description
            "The AID of the prime (ETH40G-shelf-slot-port).";
        }
        leaf ing-police {
          yang:get-supported "true";
          type enumeration {
            enum ENABLED {
              description
                "Enable Ingress Policing";
            }
            enum DISABLED {
              description
                "Disable Ingress Policing";
            }
          }
          description
            "Ingress Policing. Only supported on the OTN FlexMOTR.";
        }
        leaf cir {
          default "1";
          yang:get-supported "true";
          type ciena-6500-types:INT {
            range "1..1000000";
          }
          description
            "Committed Information Rate. Measured in kb/s.";
        }
        leaf cbs-units {
          yang:get-supported "true";
          type enumeration {
            enum BYTE {
              description
                "Commited Burst Size is measured in Bytes";
            }
            enum KBYTE {
              description
                "Commited Burst Size is measured in KBytes";
            }
          }
          description
            "Committed Burst Size Units. Only supported when CBS is supported. Only supported on the OTN FlexMOTR.";
        }
        leaf cbs {
          default "12176";
          yang:get-supported "true";
          type ciena-6500-types:INT {
            range "1..131071";
          }
          description
            "Committed Burst Size";
        }
        leaf pst {
          yang:get-supported "true";
          type enumeration {
            enum IS {
              description
                "In Service";
            }
            enum IS-ANR {
              description
                "In Service - Abnormal";
            }
            enum OOS-MA {
              description
                "Out-of-service maintenance for provisioning memory administration";
            }
            enum OOS-AU {
              description
                "Out-of-service autonomous from a failure detected point of view. It is not out of service from a state point of view. Alarm is raised if the entity is not able to perform its provisioned functions";
            }
            enum OOS-AUMA {
              description
                "Out-of-service autonomous management - the entity is not able to perform its provisioned functions and is purposefully removed from service";
            }
            enum OOS-MAANR {
              description
                "Out-of-service maintenance - abnormal";
            }
          }
          description
            "Identify the primary state";
        }
        leaf-list sst {
          yang:get-supported "true";
          type enumeration {
            enum AINS {
              description
                "Auto-In-Service";
            }
            enum MT {
              description
                "Maintenance";
            }
            enum FLT {
              description
                "Fault detected in equipment";
            }
            enum LPBK {
              description
                "Loopback";
            }
            enum SGEO {
              description
                "Supporting entity outage";
            }
            enum DISCD {
              description
                "Disconnected. (no transparent traffic connection on this facility)";
            }
            enum TSGEN {
              description
                "Test set generation";
            }
            enum TSMON {
              description
                "Test set monitor";
            }
          }
          description
            "Identify the secondary state";
        }
      }
    }
  }

  rpc port-enable-flex {
    description
      "Restore Flex Facility: This command allows you to restore a facility to service. The facility goes from a maintenance state to an in-service state.";
    yang:handler "tl1";
    input {
      leaf flex {
        mandatory true;
        description
          "AID in format FLEX-shelf-slot-port, FLEX-shelf-slot-portSsubport";
        type ciena-6500-types:aid;
      }
    }
  }

  rpc port-disable-flex {
    description
      "Remove Flex Facility: This command allows you to remove the specified facility from service and put it in an out-of-service for maintenance state.";
    yang:handler "tl1";
    input {
      leaf flex {
        mandatory true;
        description
          "AID in format FLEX-shelf-slot-port, FLEX-shelf-slot-portSsubport";
        type ciena-6500-types:aid;
      }
      leaf sst {
        type ciena-6500-enums:RMVSSTMT;
        description
          "Identify Maintenance State";
      }
    }
  }

  rpc port-show-oc3 {
    description
      "Retrieve OC-3 Facility: view the attributes of an OC-3 facility.";
    yang:handler "tl1";
    input {
      leaf oc3 {
        mandatory true;
        description
          "AID in format OC3-shelf-slot-port, ALL";
        type ciena-6500-types:aid;
      }
      leaf stinfo {
        yang:get-supported "true";
        type ciena-6500-enums:BOOL_YES_NO_defaultNO;
        description
          "Specify if Section Trace information is to be included in the response.";
      }
      leaf ssbitinfo {
        yang:get-supported "true";
        type ciena-6500-enums:BOOL_YES_NO_defaultNO;
        description
          "Specify if SS Bit information is to be included in the response.";
      }
      leaf dsminfo {
        yang:get-supported "true";
        type enumeration {
          enum YES;
          enum NO;
          enum NONE {
            description
              "Not a DSM provisioned link";
          }
          enum HOSTSIDE {
            description
              "Host located intermediate line facility";
          }
          enum DSMSIDE {
            description
              "DSM located intermediate line facility";
          }
        }
        description
          "Specify if the DSM information is to be included in the response.";
      }
    }
    output {
      list output {
        leaf oc3 {
          yang:get-supported "true";
          type ciena-6500-types:IDENT;
          description
            "aid";
        }
        leaf timing-reference {
          yang:get-supported "true";
          type ciena-6500-enums:BOOL_Y_N;
          description
            "Facility is a Timing Reference.";
        }
        leaf dcc {
          yang:get-supported "true";
          type ciena-6500-enums:BOOL_Y_N;
          description
            "Facility has DCC enabled";
        }
        leaf sd-th {
          default "6";
          yang:get-supported "true";
          type ciena-6500-types:INT {
            range "5..9";
          }
          description
            "Signal degrade threshold value";
        }
        leaf stformat {
          yang:get-supported "true";
          type enumeration {
            enum NUM {
              description
                "1 byte";
            }
            enum STRING {
              description
                "16 byte";
            }
          }
          description
            "Section Trace Format";
        }
        leaf strc {
          yang:get-supported "true";
          type ciena-6500-types:STRING;
          description
            "Transmitted section trace";
        }
        leaf exp-trc {
          yang:get-supported "true";
          type ciena-6500-types:STRING;
          description
            "Expected section trace";
        }
        leaf stfmode {
          yang:get-supported "true";
          type enumeration {
            enum OFF {
              description
                "Alarms off, no traffic protection";
            }
            enum ALMONLY {
              description
                "Alarms on, no traffic protection";
            }
            enum LINEFAIL {
              description
                "Alarms on, with traffic protection";
            }
          }
          description
            "Section Trace Fail Mode";
        }
        leaf ssbitmde {
          yang:get-supported "true";
          type ciena-6500-enums:SSBITMDE;
          description
            "SS Bit mode (facility personality)";
        }
        leaf als {
          yang:get-supported "true";
          type enumeration {
            enum ENABLED;
            enum DISABLED;
          }
          description
            "Automatic Laser Shutdown";
        }
        leaf eber-thresh {
          default "3";
          yang:get-supported "true";
          type ciena-6500-types:INT {
            range "3 | 4 | 5";
          }
          description
            "Excessive bit error threshold value";
        }
        leaf port-mode {
          yang:get-supported "true";
          type enumeration {
            enum SONET;
            enum SDH;
          }
          description
            "Optical Port market preference";
        }
        leaf uneqmode {
          yang:get-supported "true";
          type enumeration {
            enum UNKNOWN {
              description
                "Unknown unequipped insertion mode";
            }
            enum STS1 {
              description
                "Insert STS1 Unequipped";
            }
            enum VC4 {
              description
                "Insert VC4 Unequipped";
            }
          }
          description
            "Unequipped Insertion Mode";
        }
        leaf ains-time-left {
          yang:get-supported "true";
          type ciena-6500-types:TIME;
          description
            "The format will be \"HH-MM\" for the time left in AINS timeout.";
        }
        leaf dsminfo {
          yang:get-supported "true";
          type enumeration {
            enum YES;
            enum NO;
            enum NONE {
              description
                "Not a DSM provisioned link";
            }
            enum HOSTSIDE {
              description
                "Host located intermediate line facility";
            }
            enum DSMSIDE {
              description
                "DSM located intermediate line facility";
            }
          }
          description
            "Specify if the DSM information is to be included in the response.";
        }
        leaf dus-override {
          yang:get-supported "true";
          type enumeration {
            enum ENABLED;
            enum DISABLED;
          }
          description
            "A parameter which allows the synchronization quality level of a line reference to be overriden even when the receiving quality level is DUS";
        }
        leaf clfi {
          yang:get-supported "true";
          type ciena-6500-types:STRING;
          description
            "Common Language Facility Identifier.Customer provisionable label for a facility.";
        }
        leaf pst {
          yang:get-supported "true";
          type enumeration {
            enum IS {
              description
                "In Service";
            }
            enum IS-ANR {
              description
                "In Service - Abnormal";
            }
            enum OOS-MA {
              description
                "Out-of-service maintenance for provisioning memory administration";
            }
            enum OOS-AU {
              description
                "Out-of-service autonomous from a failure detected point of view. It is not out of service from a state point of view. Alarm is raised if the entity is not able to perform its provisioned functions";
            }
            enum OOS-AUMA {
              description
                "Out-of-service autonomous management - the entity is not able to perform its provisioned functions and is purposefully removed from service";
            }
            enum OOS-MAANR {
              description
                "Out-of-service maintenance - abnormal.";
            }
          }
          description
            "Identify the primary state";
        }
        leaf-list sst {
          yang:get-supported "true";
          type enumeration {
            enum AINS {
              description
                "Auto-In-Service";
            }
            enum MT {
              description
                "Maintenance";
            }
            enum DISCD {
              description
                "Disconnected (no cross-connects exist on facility)";
            }
            enum LPBK {
              description
                "Loopback";
            }
            enum FLT {
              description
                "Fault detected in equipment";
            }
            enum TS {
              description
                "Test";
            }
            enum SGEO {
              description
                "Supporting entity outage";
            }
            enum WRKRX {
              description
                "Working in the receive direction";
            }
            enum WRKTX {
              description
                "Working in the transmit direction";
            }
          }
          description
            "Identify the secondary state";
        }
      }
    }
  }

  rpc port-show-oc12 {
    description
      "Retrieve OC-12 Facility: view the attributes of an OC-12 facility.";
    yang:handler "tl1";
    input {
      leaf oc12 {
        mandatory true;
        description
          "AID in format OC12-shelf-slot-port, ALL";
        type ciena-6500-types:aid;
      }
      leaf stinfo {
        yang:get-supported "true";
        type ciena-6500-enums:BOOL_YES_NO_defaultNO;
        description
          "Specify if Section Trace information is to be included in the response.";
      }
      leaf ssbitinfo {
        yang:get-supported "true";
        type ciena-6500-enums:BOOL_YES_NO_defaultNO;
        description
          "Specify if SS Bit information is to be included in the response.";
      }
    }
    output {
      list output {
        leaf oc12 {
          yang:get-supported "true";
          type ciena-6500-types:IDENT;
          description
            "aid";
        }
        leaf timing-reference {
          yang:get-supported "true";
          type ciena-6500-enums:BOOL_Y_N;
          description
            "Facility is a Timing Reference.";
        }
        leaf dcc {
          yang:get-supported "true";
          type ciena-6500-enums:BOOL_Y_N;
          description
            "Facility has DCC enabled";
        }
        leaf sd-th {
          default "6";
          yang:get-supported "true";
          type ciena-6500-types:INT {
            range "5..9";
          }
          description
            "Signal degrade threshold value";
        }
        leaf stformat {
          yang:get-supported "true";
          type enumeration {
            enum NUM {
              description
                "1 byte";
            }
            enum STRING {
              description
                "16 byte";
            }
          }
          description
            "Section Trace Format";
        }
        leaf strc {
          yang:get-supported "true";
          type ciena-6500-types:STRING;
          description
            "Transmitted section trace";
        }
        leaf exp-trc {
          yang:get-supported "true";
          type ciena-6500-types:STRING;
          description
            "Expected section trace";
        }
        leaf stfmode {
          yang:get-supported "true";
          type enumeration {
            enum OFF {
              description
                "Alarms off, no traffic protection";
            }
            enum ALMONLY {
              description
                "Alarms on, no traffic protection";
            }
            enum LINEFAIL {
              description
                "Alarms on, with traffic protection";
            }
          }
          description
            "Section Trace Fail Mode";
        }
        leaf ssbitmde {
          yang:get-supported "true";
          type ciena-6500-enums:SSBITMDE;
          description
            "SS Bit mode (facility personality)";
        }
        leaf als {
          yang:get-supported "true";
          type enumeration {
            enum ENABLED;
            enum DISABLED;
          }
          description
            "Automatic Laser Shutdown";
        }
        leaf eber-thresh {
          default "3";
          yang:get-supported "true";
          type ciena-6500-types:INT {
            range "3 | 4 | 5";
          }
          description
            "Excessive bit error threshold value";
        }
        leaf port-mode {
          yang:get-supported "true";
          type enumeration {
            enum SONET;
            enum SDH;
          }
          description
            "Optical Port market preference";
        }
        leaf uneqmode {
          yang:get-supported "true";
          type enumeration {
            enum UNKNOWN {
              description
                "Unknown unequipped insertion mode";
            }
            enum STS1 {
              description
                "Insert STS1 Unequipped";
            }
            enum VC4 {
              description
                "Insert VC4 Unequipped";
            }
          }
          description
            "Unequipped Insertion Mode";
        }
        leaf ains-time-left {
          yang:get-supported "true";
          type ciena-6500-types:TIME;
          description
            "The format will be \"HH-MM\" for the time left in AINS timeout.";
        }
        leaf dus-override {
          yang:get-supported "true";
          type enumeration {
            enum ENABLED;
            enum DISABLED;
          }
          description
            "A parameter which allows the synchronization quality level of a line reference to be overriden even when the receiving quality level is DUS";
        }
        leaf clfi {
          yang:get-supported "true";
          type ciena-6500-types:STRING;
          description
            "Common Language Facility Identifier.Customer provisionable label for a facility.";
        }
        leaf pst {
          yang:get-supported "true";
          type enumeration {
            enum IS {
              description
                "In Service";
            }
            enum IS-ANR {
              description
                "In Service - Abnormal";
            }
            enum OOS-MA {
              description
                "Out-of-service maintenance for provisioning memory administration";
            }
            enum OOS-AU {
              description
                "Out-of-service autonomous from a failure detected point of view. It is not out of service from a state point of view. Alarm is raised if the entity is not able to perform its provisioned functions";
            }
            enum OOS-AUMA {
              description
                "Out-of-service autonomous management - the entity is not able to perform its provisioned functions and is purposefully removed from service";
            }
            enum OOS-MAANR {
              description
                "Out-of-service maintenance - abnormal.";
            }
          }
          description
            "Identify the primary state";
        }
        leaf-list sst {
          yang:get-supported "true";
          type enumeration {
            enum AINS {
              description
                "Auto-In-Service";
            }
            enum MT {
              description
                "Maintenance";
            }
            enum DISCD {
              description
                "Disconnected (no cross-connects exist on facility)";
            }
            enum LPBK {
              description
                "Loopback";
            }
            enum FLT {
              description
                "Fault detected in equipment";
            }
            enum TS {
              description
                "Test";
            }
            enum SGEO {
              description
                "Supporting entity outage";
            }
            enum WRKRX {
              description
                "Working in the receive direction";
            }
            enum WRKTX {
              description
                "Working in the transmit direction";
            }
          }
          description
            "Identify the secondary state";
        }
      }
    }
  }

  rpc port-show-oc48 {
    description
      "Retrieve OC-48 Facility: view the attributes of an OC-48 facility.";
    yang:handler "tl1";
    input {
      leaf oc48 {
        mandatory true;
        description
          "AID in format OC48-shelf-slot-port, ALL";
        type ciena-6500-types:aid;
      }
      leaf stinfo {
        yang:get-supported "true";
        type ciena-6500-enums:BOOL_YES_NO_defaultNO;
        description
          "Specify if Section Trace information is to be included in the response.";
      }
      leaf ssbitinfo {
        yang:get-supported "true";
        type ciena-6500-enums:BOOL_YES_NO_defaultNO;
        description
          "Specify if SS Bit information is to be included in the response.";
      }
    }
    output {
      list output {
        leaf oc48 {
          yang:get-supported "true";
          type ciena-6500-types:IDENT;
          description
            "aid";
        }
        leaf timing-reference {
          yang:get-supported "true";
          type ciena-6500-enums:BOOL_Y_N;
          description
            "Facility is a Timing Reference.";
        }
        leaf dcc {
          yang:get-supported "true";
          type ciena-6500-enums:BOOL_Y_N;
          description
            "Facility has DCC enabled";
        }
        leaf sd-th {
          default "6";
          yang:get-supported "true";
          type ciena-6500-types:INT {
            range "5..9";
          }
          description
            "Signal degrade threshold value";
        }
        leaf stformat {
          yang:get-supported "true";
          type enumeration {
            enum NUM {
              description
                "1 byte";
            }
            enum STRING {
              description
                "16 byte";
            }
          }
          description
            "Section Trace Format";
        }
        leaf strc {
          yang:get-supported "true";
          type ciena-6500-types:STRING;
          description
            "Transmitted section trace";
        }
        leaf exp-trc {
          yang:get-supported "true";
          type ciena-6500-types:STRING;
          description
            "Expected section trace";
        }
        leaf stfmode {
          yang:get-supported "true";
          type enumeration {
            enum OFF {
              description
                "Alarms off, no traffic protection";
            }
            enum ALMONLY {
              description
                "Alarms on, no traffic protection";
            }
            enum LINEFAIL {
              description
                "Alarms on, traffic protection (OC48 facilities only)";
            }
          }
          description
            "Section Trace Fail Mode";
        }
        leaf ssbitmde {
          yang:get-supported "true";
          type ciena-6500-enums:SSBITMDE;
          description
            "SS Bit mode (facility personality)";
        }
        leaf als {
          yang:get-supported "true";
          type enumeration {
            enum ENABLED;
            enum DISABLED;
          }
          description
            "Automatic Laser Shutdown";
        }
        leaf eber-thresh {
          default "3";
          yang:get-supported "true";
          type ciena-6500-types:INT {
            range "3 | 4 | 5";
          }
          description
            "Excessive bit error threshold value";
        }
        leaf port-mode {
          yang:get-supported "true";
          type enumeration {
            enum SONET;
            enum SDH;
          }
          description
            "Optical Port market preference";
        }
        leaf uneqmode {
          yang:get-supported "true";
          type enumeration {
            enum UNKNOWN {
              description
                "Unknown unequipped insertion mode";
            }
            enum STS1 {
              description
                "Insert STS1 Unequipped";
            }
            enum VC4 {
              description
                "Insert VC4 Unequipped";
            }
          }
          description
            "Unequipped Insertion Mode";
        }
        leaf ains-time-left {
          yang:get-supported "true";
          type ciena-6500-types:TIME;
          description
            "The format will be \"HH-MM\" for the time left in AINS timeout.";
        }
        leaf och-rx-act-power {
          yang:get-supported "true";
          type ciena-6500-types:STRING;
          description
            "RX actual power in dBm (xx.x)";
        }
        leaf och-tx-act-power {
          yang:get-supported "true";
          type ciena-6500-types:STRING;
          description
            "TX actual power in dBm (xx.x)";
        }
        leaf och-rx-min-power {
          yang:get-supported "true";
          type ciena-6500-types:STRING;
          description
            "RX minimum power in dBm (xx.x)";
        }
        leaf och-rx-max-power {
          yang:get-supported "true";
          type ciena-6500-types:STRING;
          description
            "RX maximum power in dBm (xx.x)";
        }
        leaf och-tx-min-power {
          yang:get-supported "true";
          type ciena-6500-types:STRING;
          description
            "TX minimum power in dBm (xx.x)";
        }
        leaf och-tx-max-power {
          yang:get-supported "true";
          type ciena-6500-types:STRING;
          description
            "TX maximum power in dBm (xx.x)";
        }
        leaf dus-override {
          yang:get-supported "true";
          type enumeration {
            enum ENABLED;
            enum DISABLED;
          }
          description
            "A parameter which allows the synchronization quality level of a line reference to be overriden even when the receiving quality level is DUS";
        }
        leaf clfi {
          yang:get-supported "true";
          type ciena-6500-types:STRING;
          description
            "Common Language Facility Identifier.Customer provisionable label for a facility.";
        }
        leaf rout-sig-disabled {
          yang:get-supported "true";
          type enumeration {
            enum NO {
              description
                "Used by control plane";
            }
            enum YES {
              description
                "Not used by control plane";
            }
          }
          description
            "This attribute controls whether the underlying interface will be used by control plane for I-NNI routing and signaling purposes.";
        }
        leaf pst {
          yang:get-supported "true";
          type enumeration {
            enum IS {
              description
                "In Service";
            }
            enum IS-ANR {
              description
                "In Service - Abnormal";
            }
            enum OOS-MA {
              description
                "Out-of-service maintenance for provisioning memory administration";
            }
            enum OOS-AU {
              description
                "Out-of-service autonomous from a failure detected point of view. It is not out of service from a state point of view. Alarm is raised if the entity is not able to perform its provisioned functions";
            }
            enum OOS-AUMA {
              description
                "Out-of-service autonomous management - the entity is not able to perform its provisioned functions and is purposefully removed from service";
            }
            enum OOS-MAANR {
              description
                "Out-of-service maintenance - abnormal.";
            }
          }
          description
            "Identify the primary state";
        }
        leaf-list sst {
          yang:get-supported "true";
          type enumeration {
            enum AINS {
              description
                "Auto-In-Service";
            }
            enum MT {
              description
                "Maintenance";
            }
            enum DISCD {
              description
                "Disconnected (no cross-connects exist on facility)";
            }
            enum LPBK {
              description
                "Loopback";
            }
            enum FLT {
              description
                "Fault detected in equipment";
            }
            enum TS {
              description
                "Test";
            }
            enum SGEO {
              description
                "Supporting entity outage";
            }
            enum WRKRX {
              description
                "Working in the receive direction";
            }
            enum WRKTX {
              description
                "Working in the transmit direction";
            }
          }
          description
            "Identify the secondary state";
        }
      }
    }
  }

  rpc port-disable-oc192 {
    description
      "Remove OC-192 Facility: This command allows you to remove the specified facility from service and put it in an out-of-service for maintenance state.";
    yang:handler "tl1";
    input {
      leaf oc192 {
        mandatory true;
        description
          "AID in format OC192-shelf-slot-port, OC192-shelf-slot-portSsubport";
        type ciena-6500-types:aid;
      }
      leaf sst {
        type ciena-6500-enums:RMVSSTMT;
        description
          "Identify Maintenance State";
      }
    }
  }

  rpc port-enable-oc192 {
    description
      "Restore OC-192 Facility: This command allows you to restore a facility to service. The facility goes from a maintenance state to an in-service state.";
    yang:handler "tl1";
    input {
      leaf oc192 {
        mandatory true;
        description
          "AID in format OC192-shelf-slot-port, OC192-shelf-slot-portSsubport";
        type ciena-6500-types:aid;
      }
    }
  }

  rpc port-show-oc192 {
    description
      "Retrieve OC-192 Facility: view the attributes of an OC-192 facility.";
    yang:handler "tl1";
    input {
      leaf oc192 {
        mandatory true;
        description
          "AID in format OC192-shelf-slot-port, ALL, OC192-shelf-slot-portSsubport";
        type ciena-6500-types:aid;
      }
      leaf stinfo {
        yang:get-supported "true";
        type enumeration {
          enum NO {
            description
              "Do not include Section Trace information in the response";
          }
          enum YES {
            description
              "Include Section Trace information in the response";
          }
        }
        description
          "Specify if Section Trace information is to be included in the response.";
      }
      leaf ssbitinfo {
        yang:get-supported "true";
        type enumeration {
          enum NO {
            description
              "Do not include SS bit information in the response";
          }
          enum YES {
            description
              "Do not include SS bit information in the response";
          }
        }
        description
          "Specify if SS Bit information is to be included in the response.";
      }
      leaf statsinfo {
        yang:get-supported "true";
        type enumeration {
          enum NO {
            description
              "Do not include Dynamic Status information in the response";
          }
          enum YES {
            description
              "Include Dynamic Status information in the response";
          }
        }
        description
          "Specify if Dynamic Status Information is to be included in the response.";
      }
    }
    output {
      list output {
        leaf oc192 {
          yang:get-supported "true";
          type ciena-6500-types:IDENT;
          description
            "aid";
        }
        leaf timing-reference {
          yang:get-supported "true";
          type ciena-6500-enums:BOOL_Y_N;
          description
            "Facility is a Timing Reference.";
        }
        leaf dcc {
          yang:get-supported "true";
          type ciena-6500-enums:BOOL_Y_N;
          description
            "Facility has DCC enabled";
        }
        leaf sd-th {
          default "6";
          yang:get-supported "true";
          type ciena-6500-types:INT {
            range "5..9";
          }
          description
            "Signal degrade threshold value";
        }
        leaf stformat {
          yang:get-supported "true";
          type enumeration {
            enum NUM {
              description
                "1 byte";
            }
            enum STRING {
              description
                "16 byte";
            }
          }
          description
            "Section Trace Format";
        }
        leaf strc {
          yang:get-supported "true";
          type ciena-6500-types:STRING;
          description
            "Transmitted section trace";
        }
        leaf exp-trc {
          yang:get-supported "true";
          type ciena-6500-types:STRING;
          description
            "Expected section trace";
        }
        leaf stfmode {
          yang:get-supported "true";
          type enumeration {
            enum OFF {
              description
                "Alarms off, no traffic protection";
            }
            enum ALMONLY {
              description
                "Alarms on, no traffic protection";
            }
            enum LINEFAIL {
              description
                "Alarms on, with traffic protection";
            }
          }
          description
            "Section Trace Fail Mode";
        }
        leaf port-mode {
          yang:get-supported "true";
          type enumeration {
            enum SONET;
            enum SDH;
          }
          description
            "Optical Port market preference";
        }
        leaf uneqmode {
          yang:get-supported "true";
          type enumeration {
            enum UNKNOWN {
              description
                "Unknown unequipped insertion mode";
            }
            enum STS1 {
              description
                "Insert STS1 Unequipped";
            }
            enum VC4 {
              description
                "Insert VC4 Unequipped";
            }
          }
          description
            "Unequipped Insertion Mode";
        }
        leaf ains-time-left {
          yang:get-supported "true";
          type ciena-6500-types:TIME;
          description
            "The format will be \"HH-MM\" for the time left in AINS timeout.";
        }
        leaf och-rx-act-power {
          yang:get-supported "true";
          type ciena-6500-types:STRING;
          description
            "RX actual power in dBm (xx.x)";
        }
        leaf och-rx-min-power {
          yang:get-supported "true";
          type ciena-6500-types:STRING;
          description
            "RX minimum power in dBm (xx.x)";
        }
        leaf och-rx-max-power {
          yang:get-supported "true";
          type ciena-6500-types:STRING;
          description
            "RX maximum power in dBm (xx.x)";
        }
        leaf och-tx-act-power {
          yang:get-supported "true";
          type ciena-6500-types:STRING;
          description
            "TX actual power in dBm (xx.x)";
        }
        leaf och-tx-min-power {
          yang:get-supported "true";
          type ciena-6500-types:STRING;
          description
            "TX minimum power in dBm (xx.x)";
        }
        leaf och-tx-max-power {
          yang:get-supported "true";
          type ciena-6500-types:STRING;
          description
            "TX maximum power in dBm (xx.x)";
        }
        leaf ochtxwvlngthprov {
          yang:get-supported "true";
          type ciena-6500-types:STRING;
          description
            "Provisioned Wavelength in nm (xxxx.xx)";
        }
        leaf ochtxwvlngthmin {
          default "0.00";
          yang:get-supported "true";
          type ciena-6500-types:STRING;
          description
            "Minimum Wavelength value in nm (xxxx.xx)";
        }
        leaf ochtxwvlngthmax {
          default "0.00";
          yang:get-supported "true";
          type ciena-6500-types:STRING;
          description
            "Maximum Wavelength value in nm (xxxx.xx)";
        }
        leaf ochtxwvlngthspacing {
          yang:get-supported "true";
          type ciena-6500-types:STRING;
          description
            "OCH Wavelength Spacing in Ghz";
        }
        leaf splimgmt {
          yang:get-supported "true";
          type ciena-6500-enums:spliMgmt;
          description
            "Identify if Port is Manageable by SPLI";
        }
        leaf splimanaged {
          yang:get-supported "true";
          type ciena-6500-enums:spliManaged;
          description
            "Identify if Port is Currently Managed by SPLI";
        }
        leaf laserofffarendfail {
          yang:get-supported "true";
          type ciena-6500-enums:Laserofffarendfail;
          description
            "Loss of light feature";
        }
        leaf mapping {
          yang:get-supported "true";
          type enumeration {
            enum NONE {
              description
                "Not Mapped";
            }
            enum AMP {
              description
                "AMP Mapping";
            }
            enum BMP {
              description
                "BMP Mapping";
            }
          }
          description
            "Signal Mapping";
        }
        leaf ste {
          yang:get-supported "true";
          type enumeration {
            enum YES {
              description
                "Facility is section terminating.";
            }
            enum NO {
              description
                "Facility is section transparent.";
            }
          }
          description
            "Section Terminating";
        }
        leaf ssbitmde {
          yang:get-supported "true";
          type enumeration {
            enum SONET;
            enum SDH;
          }
          description
            "SS Bit mode (facility personality)";
        }
        leaf als {
          yang:get-supported "true";
          type enumeration {
            enum ENABLED;
            enum DISABLED;
          }
          description
            "Automatic Laser Shutdown";
        }
        leaf fec {
          yang:get-supported "true";
          type ciena-6500-enums:FEC;
          description
            "FEC";
        }
        leaf nls {
          yang:get-supported "true";
          type ciena-6500-enums:BOOL_ON_OFF;
          description
            "Non Linear Supression compensation";
        }
        leaf eber-thresh {
          default "3";
          yang:get-supported "true";
          type ciena-6500-types:INT {
            range "3 | 4 | 5";
          }
          description
            "Excessive bit error threshold value";
        }
        leaf sf-th {
          default "4";
          yang:get-supported "true";
          type ciena-6500-types:INT {
            range "4..8";
          }
          description
            "Signal Fail Threshold value";
        }
        leaf dus-override {
          yang:get-supported "true";
          type enumeration {
            enum ENABLED;
            enum DISABLED;
          }
          description
            "A parameter which allows the synchronization quality level of a line reference to be overriden even when the receiving quality level is DUS";
        }
        leaf clfi {
          yang:get-supported "true";
          type ciena-6500-types:STRING;
          description
            "Common Language Facility Identifier.Customer provisionable label for a facility.";
        }
        leaf rout-sig-disabled {
          yang:get-supported "true";
          type enumeration {
            enum NO {
              description
                "Used by control plane";
            }
            enum YES {
              description
                "Not used by control plane";
            }
          }
          description
            "This attribute controls whether the underlying interface will be used by control plane for I-NNI routing and signaling purposes.";
        }
        leaf pst {
          yang:get-supported "true";
          type enumeration {
            enum IS {
              description
                "In Service";
            }
            enum IS-ANR {
              description
                "In Service - Abnormal";
            }
            enum OOS-MA {
              description
                "Out-of-service maintenance for provisioning memory administration";
            }
            enum OOS-AU {
              description
                "Out-of-service autonomous from a failure detected point of view. It is not out of service from a state point of view. Alarm is raised if the entity is not able to perform its provisioned functions";
            }
            enum OOS-AUMA {
              description
                "Out-of-service autonomous management - the entity is not able to perform its provisioned functions and is purposefully removed from service";
            }
            enum OOS-MAANR {
              description
                "Out-of-service maintenance - abnormal.";
            }
          }
          description
            "Identify the primary state";
        }
        leaf-list sst {
          yang:get-supported "true";
          type enumeration {
            enum AINS {
              description
                "Auto-In-Service";
            }
            enum MT {
              description
                "Maintenance";
            }
            enum DISCD {
              description
                "Disconnected (no cross-connects exist on facility)";
            }
            enum LPBK {
              description
                "Loopback";
            }
            enum FLT {
              description
                "Fault detected in equipment";
            }
            enum TS {
              description
                "Test";
            }
            enum SGEO {
              description
                "Supporting entity outage";
            }
            enum WRKRX {
              description
                "Working in the receive direction";
            }
            enum WRKTX {
              description
                "Working in the transmit direction";
            }
            enum TSGEN {
              description
                "Test set generation";
            }
            enum TSMON {
              description
                "Test set monitor";
            }
          }
          description
            "Identify the secondary state";
        }
      }
    }
  }

  rpc port-disable-oc768 {
    description
      "Remove OC-768 Facility: This command allows you to remove the specified facility from service and put it in an out-of-service for maintenance state.";
    yang:handler "tl1";
    input {
      leaf oc768 {
        mandatory true;
        description
          "AID in format OC768-shelf-slot-port";
        type ciena-6500-types:aid;
      }
      leaf sst {
        type ciena-6500-enums:RMVSSTMT;
        description
          "Identify Maintenance State";
      }
    }
  }

  rpc port-enable-oc768 {
    description
      "Restore OC-768 Facility: This command allows you to restore a facility to service. The facility goes from a maintenance state to an in-service state.";
    yang:handler "tl1";
    input {
      leaf oc768 {
        mandatory true;
        description
          "AID in format OC768-shelf-slot-port";
        type ciena-6500-types:aid;
      }
    }
  }

  rpc port-show-oc768 {
    description
      "Retrieve OC-768 Facility: view the attributes of an OC-768 facility.";
    yang:handler "tl1";
    input {
      leaf oc768 {
        mandatory true;
        description
          "AID in format OC768-shelf-slot-port, ALL";
        type ciena-6500-types:aid;
      }
      leaf stinfo {
        yang:get-supported "true";
        type enumeration {
          enum NO {
            description
              "Do not include Section Trace information in the response";
          }
          enum YES {
            description
              "Include Section Trace information in the response";
          }
        }
        description
          "Specify if Section Trace information is to be included in the response.";
      }
      leaf statsinfo {
        yang:get-supported "true";
        type enumeration {
          enum NO {
            description
              "Do not include Dynamic Status information in the response";
          }
          enum YES {
            description
              "Include Dynamic Status information in the response";
          }
        }
        description
          "Specify if Dynamic Status Information is to be included in the response.";
      }
    }
    output {
      list output {
        leaf oc768 {
          yang:get-supported "true";
          type ciena-6500-types:IDENT;
          description
            "aid";
        }
        leaf stformat {
          yang:get-supported "true";
          type enumeration {
            enum NUM {
              description
                "1 byte";
            }
            enum STRING {
              description
                "16 byte";
            }
          }
          description
            "Section Trace Format";
        }
        leaf strc {
          yang:get-supported "true";
          type ciena-6500-types:STRING;
          description
            "Transmitted section trace";
        }
        leaf exp-trc {
          yang:get-supported "true";
          type ciena-6500-types:STRING;
          description
            "Expected section trace";
        }
        leaf stfmode {
          yang:get-supported "true";
          type enumeration {
            enum OFF {
              description
                "Alarms off, no traffic protection";
            }
            enum ALMONLY {
              description
                "Alarms on, no traffic protection";
            }
          }
          description
            "Section Trace Fail Mode";
        }
        leaf port-mode {
          yang:get-supported "true";
          type enumeration {
            enum SONET;
            enum SDH;
          }
          description
            "Optical Port market preference";
        }
        leaf ains-time-left {
          yang:get-supported "true";
          type ciena-6500-types:TIME;
          description
            "The format will be \"HH-MM\" for the time left in AINS timeout.";
        }
        leaf och-rx-act-power {
          yang:get-supported "true";
          type ciena-6500-types:STRING;
          description
            "RX actual power in dBm (xx.x)";
        }
        leaf och-rx-min-power {
          yang:get-supported "true";
          type ciena-6500-types:STRING;
          description
            "RX minimum power in dBm (xx.x)";
        }
        leaf och-rx-max-power {
          yang:get-supported "true";
          type ciena-6500-types:STRING;
          description
            "RX maximum power in dBm (xx.x)";
        }
        leaf och-tx-act-power {
          yang:get-supported "true";
          type ciena-6500-types:STRING;
          description
            "TX actual power in dBm (xx.x)";
        }
        leaf och-tx-min-power {
          yang:get-supported "true";
          type ciena-6500-types:STRING;
          description
            "TX minimum power in dBm (xx.x)";
        }
        leaf och-tx-max-power {
          yang:get-supported "true";
          type ciena-6500-types:STRING;
          description
            "TX maximum power in dBm (xx.x)";
        }
        leaf laserofffarendfail {
          yang:get-supported "true";
          type ciena-6500-enums:Laserofffarendfail;
          description
            "Loss of light feature. Under certain scenarios insert Loss of Light (i.e. turn off the TX laser).";
        }
        leaf eber-thresh {
          default "3";
          yang:get-supported "true";
          type ciena-6500-types:INT {
            range "3 | 4 | 5";
          }
          description
            "Excessive bit error threshold value";
        }
        leaf clfi {
          yang:get-supported "true";
          type ciena-6500-types:STRING;
          description
            "Common Language Facility Identifier.Customer provisionable label for a facility.";
        }
        leaf hold-off {
          default "0";
          yang:get-supported "true";
          type ciena-6500-types:INT {
            range "0 | 100 | 200 | 300 | 400 | 500 | 600 | 700 | 800 | 900 | 1000";
          }
          description
            "HoldOff signal conditioning timer";
        }
        leaf pst {
          yang:get-supported "true";
          type enumeration {
            enum IS {
              description
                "In Service";
            }
            enum IS-ANR {
              description
                "In Service - Abnormal";
            }
            enum OOS-MA {
              description
                "Out-of-service maintenance for provisioning memory administration";
            }
            enum OOS-AU {
              description
                "Out-of-service autonomous from a failure detected point of view. It is not out of service from a state point of view. Alarm is raised if the entity is not able to perform its provisioned functions";
            }
            enum OOS-AUMA {
              description
                "Out-of-service autonomous management - the entity is not able to perform its provisioned functions and is purposefully removed from service";
            }
            enum OOS-MAANR {
              description
                "Out-of-service maintenance - abnormal.";
            }
          }
          description
            "Identify the primary state";
        }
        leaf-list sst {
          yang:get-supported "true";
          type enumeration {
            enum AINS {
              description
                "Auto-In-Service";
            }
            enum DISCD {
              description
                "Disconnected (no cross-connects exist on facility)";
            }
            enum MT {
              description
                "Maintenance";
            }
            enum LPBK {
              description
                "Loopback";
            }
            enum FLT {
              description
                "Fault detected in equipment";
            }
            enum SGEO {
              description
                "Supporting entity outage";
            }
            enum TSGEN {
              description
                "Test set generation";
            }
            enum TSMON {
              description
                "Test set monitor";
            }
          }
          description
            "Identify the secondary state";
        }
      }
    }
  }

  rpc port-show-otm2 {
    description
      "Retrieve parameters against the OTM2 Facility";
    yang:handler "tl1";
    input {
      leaf otm2aid {
        mandatory true;
        description
          "AID in format OTM2-shelf-slot-port, OTM2-shelf-slot-portSsubport";
        type ciena-6500-types:aid;
      }
      leaf tti-info {
        yang:get-supported "true";
        type enumeration {
          enum NO {
            description
              "Do not include TTI information in the response";
          }
          enum YES {
            description
              "Include TTI information in the response";
          }
        }
        description
          "Specify if TTI Information is to be included in the response (default is NO).";
      }
      leaf stats-info {
        yang:get-supported "true";
        type enumeration {
          enum NO {
            description
              "Do not include Dynamic Status information in the response";
          }
          enum YES {
            description
              "Include Dynamic Status information in the response";
          }
        }
        description
          "Specify if Dynamic Status Information is to be included in the response (default is YES).";
      }
      leaf otm-flags {
        yang:get-supported "true";
        type enumeration {
          enum NO {
            description
              "Do not include detailed OTM (OTU, OPU, ODU) termination and monitoring information in the response";
          }
          enum YES {
            description
              "Include detailed OTM (OTU, OPU, ODU) termination and monitoring in the response";
          }
        }
        description
          "Specify if OTM (OPU, ODU, OTU) Layer termination and monitoring indicators are to be included in the response (default is NO).";
      }
    }
    output {
      list output {
        leaf otm2aid {
          yang:get-supported "true";
          type ciena-6500-types:IDENT;
          description
            "aid";
        }
        leaf osid {
          yang:get-supported "true";
          type string {
            length "0..8";
          }
          description
            "8 Byte OSID identifier";
        }
        leaf tx-fec-frmt {
          yang:get-supported "true";
          type enumeration {
            enum OFF {
              description
                "NO FEC";
            }
            enum PFEC {
              description
                "Product FEC";
            }
            enum RS8 {
              description
                "Reed Solomon 8";
            }
            enum UFEC {
              description
                "7% UFEC";
            }
            enum SCFEC {
              description
                "Super Concatenated FEC";
            }
            enum BCH20 {
              description
                "BCH20 FEC";
            }
            enum QFEC {
              description
                " QFEC";
            }
            enum EFEC {
              description
                "EFEC";
            }
            enum LDPCFEC {
              description
                "LDPCFEC";
            }
          }
          description
            "TX Supported FEC";
        }
        leaf rx-fec-frmt {
          yang:get-supported "true";
          type enumeration {
            enum OFF {
              description
                "NO FEC";
            }
            enum PFEC {
              description
                "Product FEC";
            }
            enum RS8 {
              description
                "Reed Solomon 8";
            }
            enum UFEC {
              description
                "7% UFEC";
            }
            enum SCFEC {
              description
                "Super Concatenated FEC";
            }
            enum BCH20 {
              description
                "BCH20 FEC";
            }
          }
          description
            "RX Supported FEC";
        }
        leaf odu-term {
          yang:get-supported "true";
          type enumeration {
            enum YES {
              description
                "Indicates that ODU TTI is terminated on this OTM2 facility.";
            }
            enum NO {
              description
                "Indicates that ODU TTI is not terminated on this OTM2 facility.";
            }
          }
          description
            "ODUTTITERM parameter has been introduced in the RTRV-OTM2 TL-1 commands. Values it takes on are ?YES? and ?NO?. ODUTTITERM values:?YES?: means that ODU TTI is terminated on this particular OTM2 facility and Site Manager should display ODU TTI and allow provisioning / monitoring of all ODU TTI parameters.?NO?: means that ODU TTI is not terminated on this port and SM should not display the ODU TTI parameters except the ODU TTI RX Incoming value. The 6500 BB packs (10GOTR/10GOTSC, 40GMUX, 2x10G OTR, 4x10G OTR, and OTNWT) that act as a regen will passthrough ODU TTI but will allow for the monitoring of ODU TTI RX Incoming value.When there is no client facilty, ODU TTI is not terminated. Default is NO since the client facility does not autoprov. If client facility is not an OTM2, then this port terminates ODU TTI (Terminal). If client facility is OTM2, then this port does not terminate ODU TTI (Regen).";
        }
        leaf otu-tx-tti {
          yang:get-supported "true";
          type ciena-6500-types:STRING;
          description
            "Transmitted TTI 32B. TTI =OTU Trail Trace Identifier";
        }
        leaf odu-tx-tti {
          yang:get-supported "true";
          type ciena-6500-types:STRING;
          description
            "Transmitted TTI 32B. TTI =ODU Trail Trace Identifier";
        }
        leaf otu-rx-exp-tti {
          yang:get-supported "true";
          type ciena-6500-types:STRING;
          description
            "Expected 32 Characters OTU TTI";
        }
        leaf odu-rx-exp-tti {
          yang:get-supported "true";
          type ciena-6500-types:STRING;
          description
            "Expected 32 Characters ODU TTI";
        }
        leaf otu-tx-sapi {
          yang:get-supported "true";
          type ciena-6500-types:STRING;
          description
            "OTU Transmitted SAPI TTI (15 Characters). TTI = Trail Trace Identifier";
        }
        leaf otu-tx-dapi {
          yang:get-supported "true";
          type ciena-6500-types:STRING;
          description
            "OTU Transmitted DAPI TTI (15 Characters). TTI = Trail Trace Identifier";
        }
        leaf otu-exp-sapi {
          yang:get-supported "true";
          type ciena-6500-types:STRING;
          description
            "OTU Expected SAPI TTI (15 Characters)";
        }
        leaf otu-exp-dapi {
          yang:get-supported "true";
          type ciena-6500-types:STRING;
          description
            "OTU Expected DAPI TTI (15 Characters)";
        }
        leaf odu-tx-sapi {
          yang:get-supported "true";
          type ciena-6500-types:STRING;
          description
            "ODU Transmitted SAPI TTI (15 Characters). TTI = Trail Trace Identifier";
        }
        leaf odu-tx-dapi {
          yang:get-supported "true";
          type ciena-6500-types:STRING;
          description
            "ODU Transmitted DAPI TTI (15 Characters). TTI = Trail Trace Identifier";
        }
        leaf odu-exp-sapi {
          yang:get-supported "true";
          type ciena-6500-types:STRING;
          description
            "ODU Expected SAPI TTI (15 Characters)";
        }
        leaf odu-exp-dapi {
          yang:get-supported "true";
          type ciena-6500-types:STRING;
          description
            "ODU Expected DAPI TTI (15 Characters)";
        }
        leaf tx-path-id {
          default "1";
          yang:get-supported "true";
          type ciena-6500-types:INT {
            range "1..254";
          }
          description
            "TX path identifier";
        }
        leaf tx-mode {
          yang:get-supported "true";
          type enumeration {
            enum ED {
              description
                "Extended Dispersion";
            }
            enum EP {
              description
                "Extended Power";
            }
          }
          description
            "Transmitter Dispersion Mode";
        }
        leaf tx-pwr {
          yang:get-supported "true";
          type ciena-6500-types:STRING;
          description
            "Provisioned TX Power in dBm (xx.x)";
        }
        leaf tx-act-pwr {
          yang:get-supported "true";
          type ciena-6500-types:STRING;
          description
            "TX actual power in dBm (xx.x)";
        }
        leaf tx-min-pwr {
          yang:get-supported "true";
          type ciena-6500-types:STRING;
          description
            "TX minimum power in dBm (xx.x)";
        }
        leaf tx-max-pwr {
          yang:get-supported "true";
          type ciena-6500-types:STRING;
          description
            "TX maximum power in dBm (xx.x)";
        }
        leaf rx-act-pwr {
          yang:get-supported "true";
          type ciena-6500-types:STRING;
          description
            "RX actual power in dBm (xx.x)";
        }
        leaf rx-min-pwr {
          yang:get-supported "true";
          type ciena-6500-types:STRING;
          description
            "RX minimum power in dBm (xx.x)";
        }
        leaf rx-max-pwr {
          yang:get-supported "true";
          type ciena-6500-types:STRING;
          description
            "RX maximum power in dBm (xx.x)";
        }
        leaf tx-wvlngth-prov {
          yang:get-supported "true";
          type ciena-6500-types:STRING;
          description
            "Provisioned Wavelength in nm (xxxx.xx)";
        }
        leaf tx-wvlngth-min {
          default "0.00";
          yang:get-supported "true";
          type ciena-6500-types:STRING;
          description
            "Minimum Wavelength value in nm (xxxx.xx)";
        }
        leaf tx-wvlngth-max {
          default "0.00";
          yang:get-supported "true";
          type ciena-6500-types:STRING;
          description
            "Maximum Wavelength value in nm (xxxx.xx)";
        }
        leaf tx-wvlngth-spacing {
          yang:get-supported "true";
          type ciena-6500-types:STRING;
          description
            "OCH Wavelength Spacing";
        }
        leaf tx-tr-cont {
          yang:get-supported "true";
          type enumeration {
            enum ON {
              description
                "Dispersion Control";
            }
            enum OFF;
          }
          description
            "TR Control";
        }
        leaf tx-tr-cont-state {
          yang:get-supported "true";
          type enumeration {
            enum TRCONTOFF {
              description
                "TR Control OFF";
            }
            enum IDLE {
              description
                "TX Wavelength not provisioned.";
            }
            enum UNKNOWN;
            enum DISPSCANINPROG {
              description
                "Dispersion Scan in progress";
            }
            enum OOSOPTIMIZATION {
              description
                "Out of service optimization";
            }
            enum ISOPTIMIZATION {
              description
                "In service optimization";
            }
            enum ISOPTIMIZATIONHOLDOVER {
              description
                "In service optimization in Holdover";
            }
            enum SSOPTIMIZATION {
              description
                "Steady State Optimization";
            }
          }
          description
            "TR Control State";
        }
        leaf tx-disp-prov {
          default "0";
          yang:get-supported "true";
          type ciena-6500-types:INT;
          description
            "Transmitter Dispersion Value";
        }
        leaf tx-act-disp {
          yang:get-supported "true";
          type union {
            type enumeration {
              enum UNKNOWN;
            }
            type ciena-6500-types:INT;
          }
          description
            "Transmitter actual Dispersion Value";
        }
        leaf tx-disp-min {
          yang:get-supported "true";
          type ciena-6500-types:INT;
          description
            "Minimum Transmitter Dispersion Value";
        }
        leaf tx-disp-max {
          yang:get-supported "true";
          type ciena-6500-types:INT;
          description
            "Maximum Transmitter Dispersion Value";
        }
        leaf rx-act-disp {
          yang:get-supported "true";
          type union {
            type enumeration {
              enum UNKNOWN;
            }
            type ciena-6500-types:INT;
          }
          description
            "TR Control RX Last Acquired Dispersion";
        }
        leaf rx-echo-trace {
          yang:get-supported "true";
          type ciena-6500-types:STRING;
          description
            "TR Transmit Identifier Received";
        }
        leaf tx-trace {
          yang:get-supported "true";
          type ciena-6500-types:STRING;
          description
            "TR Transmit Identifier Received Expected";
        }
        leaf tx-assoc-far-end-rx {
          yang:get-supported "true";
          type ciena-6500-types:STRING;
          description
            "Transmitter associated far end receiver";
        }
        leaf tx-sbs {
          yang:get-supported "true";
          type enumeration {
            enum ON {
              description
                "SBS Dither";
            }
            enum OFF;
          }
          description
            "Stimulated Brillouin Scattering compensation Dither";
        }
        leaf tx-am-frmt {
          yang:get-supported "true";
          type enumeration {
            enum AM1;
            enum AM2;
            enum AM1IDLER;
            enum AM2IDLER;
            enum OFF;
          }
          description
            "TX AM format";
        }
        leaf port-mode {
          yang:get-supported "true";
          type enumeration {
            enum SONET {
              description
                "Optical port market";
            }
            enum SDH;
          }
          description
            "Optical port Market preference";
        }
        leaf tf-mode {
          yang:get-supported "true";
          type enumeration {
            enum OFF {
              description
                "Alarms off, no traffic protection";
            }
            enum ALMONLY {
              description
                "Alarms on, no traffic protection";
            }
          }
          description
            "OTU Trace Fail Mode";
        }
        leaf odu-tf-mode {
          yang:get-supported "true";
          type enumeration {
            enum OFF {
              description
                "Alarms off, no traffic protection";
            }
            enum ALMONLY {
              description
                "Alarms on, no traffic protection";
            }
          }
          description
            "ODU Trace Fail Mode";
        }
        leaf otu-timen {
          yang:get-supported "true";
          type enumeration {
            enum OPERATOR {
              description
                "Monitor OTU Operator Specific TTI mismatch";
            }
            enum SAPI {
              description
                "Monitor OTU SAPI TTI mismatch";
            }
            enum DAPI {
              description
                "Monitor OTU DAPI TTI mismatch";
            }
            enum SAPI_DAPI {
              description
                "Monitor OTU SAPI and DAPI TTI mismatch";
            }
          }
          description
            "OTU TTI Mismatch Detection";
        }
        leaf odu-timen {
          yang:get-supported "true";
          type enumeration {
            enum OPERATOR {
              description
                "Monitor ODU Operator Specific TTI mismatch";
            }
            enum SAPI {
              description
                "Monitor ODU SAPI TTI mismatch";
            }
            enum DAPI {
              description
                "Monitor ODU DAPI TTI mismatch";
            }
            enum SAPI_DAPI {
              description
                "Monitor ODU SAPI and DAPI TTI mismatch";
            }
          }
          description
            "ODU TTI Mismatch Detection";
        }
        leaf laser-off-far-end-fail {
          yang:get-supported "true";
          type ciena-6500-enums:Laserofffarendfail;
          description
            "Enabled or Disabled LOL (Loss of Light) feature";
        }
        leaf tx-chrip {
          yang:get-supported "true";
          type enumeration {
            enum POSITIVE;
            enum NEGATIVE;
          }
          description
            "Positive or Negative Chirp setting";
        }
        leaf pre-fec-sf-th-lev {
          yang:get-supported "true";
          type ciena-6500-types:STRING;
          description
            "Pre-FEC Signal Fail Threshold Level. Parameter applies when FEC is ON";
        }
        leaf pre-fec-sf-th-ber {
          yang:get-supported "true";
          type ciena-6500-types:STRING;
          description
            "Pre-FEC Signal Fail Threshold Bit Error Rate. Parameter applies when FEC is ON";
        }
        leaf pre-fec-sd-th-lev {
          yang:get-supported "true";
          type ciena-6500-types:STRING;
          description
            "Pre-FEC Signal Degrade Threshold Level. Parameter applies when FEC is ON";
        }
        leaf pre-fec-sd-th-ber {
          yang:get-supported "true";
          type ciena-6500-types:STRING;
          description
            "Pre-FEC Signal Degrade Threshold Bit Error Rate. Parameter applies when FEC is ON";
        }
        leaf otu-rate {
          yang:get-supported "true";
          type enumeration {
            enum 9G95 {
              description
                "9.95 G connection - Typically OC192 sonet";
            }
            enum 10G709 {
              description
                "10.70 G connection - Typically OTU2/OC192/STM64/10GE WAN";
            }
            enum 11G05 {
              description
                "11.05 G connection - Typically 10GE/OTU2 Mapping";
            }
            enum 11G09 {
              description
                "11.09 G connection - Typically 10GE/OTU2 Mapping";
            }
            enum 11G27 {
              description
                "11.27 G connection - Typically Fibre Channel 1200";
            }
          }
          description
            "OTMn Rate";
        }
        leaf exp-pt {
          yang:get-supported "true";
          type ciena-6500-types:STRING;
          description
            "HEX value in the range 0x00-0xFF. This attribute is used to specify the value of Expected PT.";
        }
        leaf tx-pt {
          yang:get-supported "true";
          type ciena-6500-types:STRING;
          description
            "HEX value in the range 0x00-0xFF. This attribute is used to specify the value of Transmitted PT.";
        }
        leaf opu2-resvd {
          yang:get-supported "true";
          type enumeration {
            enum YES {
              description
                "Use 7 unused bytes of the OPU2 overhead for payload";
            }
            enum NO;
          }
          description
            "This attribute is used to specify whether to use the 7 unused bytes of the OPU2 overhead for payload or not.";
        }
        leaf odu-monitor {
          yang:get-supported "true";
          type enumeration {
            enum NO {
              description
                "Not monitor ODU Layer";
            }
            enum YES {
              description
                "Monitor ODU Layer";
            }
          }
          description
            "Indicating whether to monitor ODU Layer";
        }
        leaf otu-sd-th-lev {
          yang:get-supported "true";
          type ciena-6500-types:INT;
          description
            "OTU Signal Degrade Threshold Level, only applies when FEC is OFF";
        }
        leaf odu-sf-th-lev {
          default "0";
          yang:get-supported "true";
          type ciena-6500-types:INT;
          description
            "ODU Post-FEC Signal Fail Threshold Level";
        }
        leaf odu-sd-th-lev {
          default "0";
          yang:get-supported "true";
          type ciena-6500-types:INT;
          description
            "ODU Post-FEC Signal Degrade Threshold Level";
        }
        leaf ains-time-left {
          yang:get-supported "true";
          type ciena-6500-types:TIME;
          description
            "The format will be \"HH-MM\" for the time left in AINS timeout.";
        }
        leaf otm-term {
          yang:get-supported "true";
          type ciena-6500-types:STRING;
          description
            "OTM Termination per layer (OPU and/or ODU and/or OTU)";
        }
        leaf otm-flt-mon {
          yang:get-supported "true";
          type ciena-6500-types:STRING;
          description
            "OTM Fault Monitoring per layer (OPU and/or ODU and/or OTU)";
        }
        leaf otm-prf-mon {
          yang:get-supported "true";
          type ciena-6500-types:STRING;
          description
            "OTM Performance Monitoring per layer (OPU and/or ODU and/or OTU)";
        }
        leaf cc-tx-freq {
          yang:get-supported "true";
          type ciena-6500-types:STRING;
          description
            "Tx Sub-carrier Frequency";
        }
        leaf cc-tx-mod-depth {
          yang:get-supported "true";
          type ciena-6500-types:STRING;
          description
            "Tx Modulation Depth";
        }
        leaf cc-tx-msg-len {
          default "16";
          yang:get-supported "true";
          type ciena-6500-types:STRING;
          description
            "Tx Message Length";
        }
        leaf cc-tx-ask-baud-rate {
          yang:get-supported "true";
          type enumeration {
            enum 333.33 {
              description
                "Baud Rate";
            }
            enum 1667 {
              description
                "Baud Rate";
            }
            enum 150 {
              description
                "Baud Rate";
            }
            enum 1000 {
              description
                "Baud Rate";
            }
            enum UNKNOWN {
              description
                "Baud Rate";
            }
          }
          description
            "Tx ASK Baud Rate";
        }
        leaf cc-tx-encode-frmt {
          yang:get-supported "true";
          type enumeration {
            enum NRZ {
              description
                "Encoding Format";
            }
            enum NRZ2 {
              description
                "Encoding Format";
            }
            enum 3SB1 {
              description
                "Encoding Format";
            }
            enum 3SB2 {
              description
                "Encoding Format";
            }
            enum UNKNOWN {
              description
                "UNKNOWN Encoding Format";
            }
          }
          description
            "Tx Encoding Format";
        }
        leaf rc-rx-freq {
          yang:get-supported "true";
          type ciena-6500-types:STRING;
          description
            "Rx Sub-carrier Frequency";
        }
        leaf rc-rx-msg-len {
          default "28";
          yang:get-supported "true";
          type ciena-6500-types:STRING;
          description
            "Rx Message Length";
        }
        leaf rc-rx-ask-baud-rate {
          yang:get-supported "true";
          type enumeration {
            enum 16.67 {
              description
                "Baud Rate";
            }
            enum 83.33 {
              description
                "Baud Rate";
            }
            enum 50 {
              description
                "Baud Rate";
            }
            enum UNKNOWN {
              description
                "UNKNOWN Baud Rate";
            }
          }
          description
            "Rx ASK Baud Rate";
        }
        leaf rc-rx-bpsk-baud-rate {
          yang:get-supported "true";
          type enumeration {
            enum 150 {
              description
                "Baud Rate";
            }
            enum 5 {
              description
                "Baud Rate";
            }
            enum UNKNOWN {
              description
                "UNKNOWN Baud Rate";
            }
          }
          description
            "Rx BPSK Baud Rate";
        }
        leaf rc-rx-decode-frmt {
          yang:get-supported "true";
          type enumeration {
            enum NRZ {
              description
                "Encoding Format";
            }
            enum NRZ2 {
              description
                "Encoding Format";
            }
            enum 3SB1 {
              description
                "Encoding Format";
            }
            enum 3SB2 {
              description
                "Encoding Format";
            }
            enum UNKNOWN {
              description
                "UNKNOWN Encoding Format";
            }
          }
          description
            "Rx Decoding Format";
        }
        leaf rc-rx-thresh-mode {
          yang:get-supported "true";
          type enumeration {
            enum AUTO {
              description
                "Threshold Mode AUTO";
            }
            enum MANUAL {
              description
                "Threshold Mode MANUAL";
            }
            enum UNKNOWN {
              description
                "Threshold Mode UNKNOWN";
            }
          }
          description
            "Rx Threshold Mode";
        }
        leaf rc-rx-thresh {
          default "100";
          yang:get-supported "true";
          type ciena-6500-types:STRING;
          description
            "Rx Threshold";
        }
        leaf repeater-system-type {
          yang:get-supported "true";
          type enumeration {
            enum FAMILY_A {
              description
                "Repeater System Family A";
            }
            enum FAMILY_B {
              description
                "Repeater System Family B";
            }
            enum FAMILY_C {
              description
                "Repeater System Family C";
            }
            enum UNKNOWN {
              description
                "Repeater System Type Unknown";
            }
          }
          description
            "Repeater System Type";
        }
        leaf repeater-system-desc {
          yang:get-supported "true";
          type ciena-6500-types:STRING;
          description
            "Repeater Description";
        }
        leaf clfi {
          yang:get-supported "true";
          type ciena-6500-types:STRING;
          description
            "Common Language Facility Identifier.Customer provisionable label for a facility.";
        }
        leaf cond-type {
          yang:get-supported "true";
          type ciena-6500-enums:OTM_CONDTYPE;
          description
            "The type of conditioning";
        }
        leaf dm-enable {
          yang:get-supported "true";
          type enumeration {
            enum YES {
              description
                "Delay measurement is enabled.";
            }
            enum NO {
              description
                "Delay measurement is disabled.";
            }
          }
          description
            "Indicates whether delay measurement is enabled or disabled.";
        }
        leaf dm-count {
          yang:get-supported "true";
          type ciena-6500-types:STRING;
          description
            "Most recent delay measurement count.";
        }
        leaf fec-sf-monitor {
          yang:get-supported "true";
          type enumeration {
            enum NO {
              description
                "Do Not Monitor FECSF";
            }
            enum YES {
              description
                "Monitor FECSF";
            }
          }
          description
            "Indicates whether to monitor Far-End client signal";
        }
        leaf encr-tcm {
          default "1";
          yang:get-supported "true";
          type ciena-6500-types:INT {
            range "1..6";
          }
          description
            "Active TCM Level for Encryption";
        }
        leaf manual-trib-slots {
          yang:get-supported "true";
          type enumeration {
            enum NO {
              description
                "Manual tributary slots assignment is supported.";
            }
            enum YES {
              description
                "Manual tributary slots assignment is not supported.";
            }
          }
          description
            "Indicates whether tributary slot assignment is supported.";
        }
        leaf ts-assigned {
          yang:get-supported "true";
          type ciena-6500-types:STRING;
          description
            "Assigned tributary slot(HEX) associated with this port.";
        }
        leaf encr-odu1 {
          yang:get-supported "true";
          type ciena-6500-types:INT;
          description
            "ODU Reserve Byte 1 for Encryption";
        }
        leaf encr-odu2 {
          yang:get-supported "true";
          type ciena-6500-types:INT;
          description
            "ODU Reserve Byte 2 for Encryption";
        }
        leaf otu-oh-non-term {
          yang:get-supported "true";
          type enumeration {
            enum NONE {
              description
                "Entire GCC OH terminated";
            }
            enum GCC0 {
              description
                "GCC0 portion of OTU OH not terminated";
            }
          }
          description
            "Indicating whether to termiate GCC OH or not";
        }
        leaf spli-mgmt {
          yang:get-supported "true";
          type ciena-6500-enums:spliMgmt;
          description
            "Identify if Port is Manageable by SPLI";
        }
        leaf spli-managed {
          yang:get-supported "true";
          type ciena-6500-enums:spliManaged;
          description
            "Identify if Port is Currently Managed by SPLI";
        }
        leaf pst {
          yang:get-supported "true";
          type ciena-6500-enums:PSTfac_RTRV;
          description
            "Identify the primary State";
        }
        leaf-list sst {
          yang:get-supported "true";
          type enumeration {
            enum AINS {
              description
                "Auto-In-Service";
            }
            enum MT {
              description
                "Maintenance";
            }
            enum FLT {
              description
                "Fault detected";
            }
            enum SGEO {
              description
                "Supporting Entity Outage (based on PSTQ of OOS-AU, OOS-AUMA only)";
            }
            enum LPBK {
              description
                "Loopback";
            }
            enum DISCD {
              description
                "Disconnected. (no transparent traffic connection on this facility)";
            }
            enum TSGEN {
              description
                "Test set generation";
            }
            enum TSMON {
              description
                "Test set monitor";
            }
            enum WRKRX {
              description
                "Active OTM2 Facility in Receiving Direction (in protection configuration only)";
            }
            enum WRKTX {
              description
                "Active OTM2 Facility in Transmitting Direction (in protection configuration only)";
            }
            enum STBYH {
              description
                "Hot Standby (in protection configuration only)";
            }
            enum PSI {
              description
                "Protection Switch Inhibited (in protection configuration only)";
            }
          }
          description
            "Secondary State";
        }
      }
    }
  }

  rpc port-disable-otm2 {
    description
      "Remove an OTM2 Facility";
    yang:handler "tl1";
    input {
      leaf otm2aid {
        mandatory true;
        description
          "AID in format OTM2-shelf-slot-port, OTM2-shelf-slot-portSsubport";
        type ciena-6500-types:aid;
      }
      leaf sst {
        type ciena-6500-enums:RMVSSTMT;
        description
          "Identify Maintenance State";
      }
    }
  }

  rpc port-enable-otm2 {
    description
      "Restore an OTM2 Facility";
    yang:handler "tl1";
    input {
      leaf otm2aid {
        mandatory true;
        description
          "AID in format OTM2-shelf-slot-port, OTM2-shelf-slot-portSsubport";
        type ciena-6500-types:aid;
      }
    }
  }

  rpc port-show-otm3 {
    description
      "Retrieve parameters against the OTM3 Facility";
    yang:handler "tl1";
    input {
      leaf otm3aid {
        mandatory true;
        description
          "AID in format OTM3-shelf-slot-port";
        type ciena-6500-types:aid;
      }
      leaf tti-info {
        yang:get-supported "true";
        type enumeration {
          enum NO {
            description
              "Do not include TTI information in the response";
          }
          enum YES {
            description
              "Include TTI information in the response";
          }
        }
        description
          "Specify if TTI Information is to be included in the response (default is NO).";
      }
      leaf stats-info {
        yang:get-supported "true";
        type enumeration {
          enum NO {
            description
              "Do not include Dynamic Status information in the response";
          }
          enum YES {
            description
              "Include Dynamic Status information in the response";
          }
        }
        description
          "Specify if Dynamic Status Information is to be included in the response (default is YES).";
      }
      leaf otm-flags {
        yang:get-supported "true";
        type enumeration {
          enum NO {
            description
              "Do not include detailed OTM (OTU, OPU, ODU) termination and monitoring information in the response";
          }
          enum YES {
            description
              "Include detailed OTM (OTU, OPU, ODU) termination and monitoring in the response";
          }
        }
        description
          "Specify if OTM (OPU, ODU, OTU) Layer termination and monitoring indicators are to be included in the response (default is NO).";
      }
    }
    output {
      list output {
        leaf otm3aid {
          yang:get-supported "true";
          type ciena-6500-types:IDENT;
          description
            "aid";
        }
        leaf osid {
          yang:get-supported "true";
          type string {
            length "0..8";
          }
          description
            "8 Byte OSID identifier";
        }
        leaf tx-fec-frmt {
          yang:get-supported "true";
          type enumeration {
            enum OFF {
              description
                "NO FEC";
            }
            enum RS8 {
              description
                "Reed Solomon 8";
            }
            enum PFEC {
              description
                "Product FEC";
            }
          }
          description
            "TX Supported FEC";
        }
        leaf rx-fec-frmt {
          yang:get-supported "true";
          type enumeration {
            enum OFF {
              description
                "NO FEC";
            }
            enum RS8 {
              description
                "Reed Solomon 8";
            }
            enum PFEC {
              description
                "Product FEC";
            }
          }
          description
            "RX Supported FEC";
        }
        leaf odu-term {
          yang:get-supported "true";
          type enumeration {
            enum YES {
              description
                "Indicates that ODU TTI is terminated on this OTM3 facility.";
            }
            enum NO {
              description
                "Indicates that ODU TTI is not terminated on this OTM3 facility.";
            }
          }
          description
            "ODUTTITERM parameter values indicate:?YES?: means that ODU TTI is terminated on this particular OTM3 facility and Site Manager should display ODU TTI and allow provisioning / monitoring of all ODU TTI parameters.?NO?: means that ODU TTI is not terminated on this port and SM should not display the ODU TTI parameters except the ODU TTI RX Incoming value. The 6500 BB circuit packs that act as regen will passthrough ODU TTI but will allow for the monitoring of ODU TTI RX Incoming value.When there is no client facility, ODU TTI is not terminated. Default is NO since the client facility does not autoprov. If client facility is not an OTM3, then this port terminates ODU TTI (Terminal). If client facility is OTM3, then this port does not terminate ODU TTI (Regen).";
        }
        leaf otu-tx-tti {
          yang:get-supported "true";
          type ciena-6500-types:STRING;
          description
            "Transmitted TTI 32B. TTI =OTU Trail Trace Identifier";
        }
        leaf odu-tx-tti {
          yang:get-supported "true";
          type ciena-6500-types:STRING;
          description
            "Transmitted TTI 32B. TTI =ODU Trail Trace Identifier";
        }
        leaf otu-rx-exp-tti {
          yang:get-supported "true";
          type ciena-6500-types:STRING;
          description
            "Expected 32 Characters OTU TTI";
        }
        leaf odu-rx-exp-tti {
          yang:get-supported "true";
          type ciena-6500-types:STRING;
          description
            "Expected 32 Characters ODU TTI";
        }
        leaf otu-tx-sapi {
          yang:get-supported "true";
          type ciena-6500-types:STRING;
          description
            "OTU Transmitted SAPI TTI (15 Characters). TTI = Trail Trace Identifier";
        }
        leaf otu-tx-dapi {
          yang:get-supported "true";
          type ciena-6500-types:STRING;
          description
            "OTU Transmitted DAPI TTI (15 Characters). TTI = Trail Trace Identifier";
        }
        leaf otu-exp-sapi {
          yang:get-supported "true";
          type ciena-6500-types:STRING;
          description
            "OTU Expected SAPI TTI (15 Characters)";
        }
        leaf otu-exp-dapi {
          yang:get-supported "true";
          type ciena-6500-types:STRING;
          description
            "OTU Expected DAPI TTI (15 Characters)";
        }
        leaf odu-tx-sapi {
          yang:get-supported "true";
          type ciena-6500-types:STRING;
          description
            "ODU Transmitted SAPI TTI (15 Characters). TTI = Trail Trace Identifier";
        }
        leaf odu-tx-dapi {
          yang:get-supported "true";
          type ciena-6500-types:STRING;
          description
            "ODU Transmitted DAPI TTI (15 Characters). TTI = Trail Trace Identifier";
        }
        leaf odu-exp-sapi {
          yang:get-supported "true";
          type ciena-6500-types:STRING;
          description
            "ODU Expected SAPI TTI (15 Characters)";
        }
        leaf odu-exp-dapi {
          yang:get-supported "true";
          type ciena-6500-types:STRING;
          description
            "ODU Expected DAPI TTI (15 Characters)";
        }
        leaf tx-path-id {
          default "1";
          yang:get-supported "true";
          type ciena-6500-types:INT {
            range "1..254";
          }
          description
            "TX path identifier";
        }
        leaf tx-pwr {
          yang:get-supported "true";
          type ciena-6500-types:STRING;
          description
            "Provisioned TX Power in dBm (xx.x)";
        }
        leaf tx-act-high-pwr {
          yang:get-supported "true";
          type ciena-6500-types:STRING;
          description
            "TX Actual High Power Value in dBm (xx.x)";
        }
        leaf tx-act-low-pwr {
          yang:get-supported "true";
          type ciena-6500-types:STRING;
          description
            "TX Actual Low Power Value in dBm (xx.x)";
        }
        leaf tx-act-pwr {
          yang:get-supported "true";
          type ciena-6500-types:STRING;
          description
            "TX actual power in dBm (xx.x)";
        }
        leaf tx-min-pwr {
          yang:get-supported "true";
          type ciena-6500-types:STRING;
          description
            "TX minimum power in dBm (xx.x)";
        }
        leaf tx-max-pwr {
          yang:get-supported "true";
          type ciena-6500-types:STRING;
          description
            "TX maximum power in dBm (xx.x)";
        }
        leaf rx-act-high-pwr {
          yang:get-supported "true";
          type ciena-6500-types:STRING;
          description
            "RX Actual High Power Value in dBm (xx.x)";
        }
        leaf rx-act-low-pwr {
          yang:get-supported "true";
          type ciena-6500-types:STRING;
          description
            "RX Actual Low Power Value in dBm (xx.x)";
        }
        leaf rx-act-pwr {
          yang:get-supported "true";
          type ciena-6500-types:STRING;
          description
            "RX actual power in dBm (xx.x)";
        }
        leaf rx-min-pwr {
          yang:get-supported "true";
          type ciena-6500-types:STRING;
          description
            "RX minimum power in dBm (xx.x)";
        }
        leaf rx-max-pwr {
          yang:get-supported "true";
          type ciena-6500-types:STRING;
          description
            "RX maximum power in dBm (xx.x)";
        }
        leaf rx-ch-act-pwr {
          yang:get-supported "true";
          type ciena-6500-types:STRING;
          description
            "RX channel actual power in dBm (xx.x)";
        }
        leaf rx-ch-min-pwr {
          yang:get-supported "true";
          type ciena-6500-types:STRING;
          description
            "RX channel minimum power in dBm (xx.x)";
        }
        leaf rx-ch-max-pwr {
          yang:get-supported "true";
          type ciena-6500-types:STRING;
          description
            "RX channel maximum power in dBm (xx.x)";
        }
        leaf pwr-bal-ctlr {
          yang:get-supported "true";
          type enumeration {
            enum DISABLED {
              description
                "Power Balance Controller Disabled";
            }
            enum ENABLED {
              description
                "Power Balance Controller Enabled";
            }
          }
          description
            "Provisioned Power Balance Controller Operating Mode";
        }
        leaf pwr-bal-offset {
          yang:get-supported "true";
          type ciena-6500-types:STRING;
          description
            "Provisioned Power Balance Offset in dB (xx.x)";
        }
        leaf pwr-bal-act-offset {
          yang:get-supported "true";
          type ciena-6500-types:STRING;
          description
            "Provisioned Power Balance Actual Offset in dB (xx.x)";
        }
        leaf tx-wvlngth-prov {
          yang:get-supported "true";
          type ciena-6500-types:STRING;
          description
            "Provisioned Wavelength in nm (xxxx.xx)";
        }
        leaf tx-wvlngth-min {
          default "0.00";
          yang:get-supported "true";
          type ciena-6500-types:STRING;
          description
            "Minimum Wavelength value in nm (xxxx.xx)";
        }
        leaf tx-wvlngth-max {
          default "0.00";
          yang:get-supported "true";
          type ciena-6500-types:STRING;
          description
            "Maximum Wavelength value in nm (xxxx.xx)";
        }
        leaf tx-wvlngth-spacing {
          yang:get-supported "true";
          type ciena-6500-types:STRING;
          description
            "OCH Wavelength Spacing";
        }
        leaf tuning-mode {
          yang:get-supported "true";
          type enumeration {
            enum NORMAL {
              description
                "Normal Tuning Mode";
            }
            enum ACCELERATED {
              description
                "Accelerated Tuning Mode";
            }
          }
          description
            "Provisioned Tuning Mode";
        }
        leaf differential-encoding {
          yang:get-supported "true";
          type enumeration {
            enum NONE {
              description
                "TR Control NONE";
            }
            enum HARD {
              description
                "TR Control HARD";
            }
            enum SOFT {
              description
                "TR Control SOFT";
            }
          }
          description
            "OCH Differential Encoding";
        }
        leaf spectral-occupancy {
          yang:get-supported "true";
          type enumeration {
            enum NONE;
            enum NARROW;
            enum WIDE20;
            enum WIDE25;
            enum WIDE30;
            enum WIDE40;
            enum WIDE50;
            enum MINSPACE20;
            enum MINSPACE25;
          }
          description
            "OCH Spectral Occupancy setting";
        }
        leaf rx-act-disp {
          yang:get-supported "true";
          type union {
            type enumeration {
              enum UNKNOWN;
            }
            type ciena-6500-types:INT;
          }
          description
            "TR Control RX Last Acquired Dispersion";
        }
        leaf max-pmd {
          yang:get-supported "true";
          type ciena-6500-types:STRING;
          description
            "Supported Mean DGD (Differential Group Delay) value";
        }
        leaf rx-act-pmd {
          yang:get-supported "true";
          type ciena-6500-types:STRING;
          description
            "Estimated Instance of DGD (Differential Group Delay) value";
        }
        leaf reach-spec {
          yang:get-supported "true";
          type ciena-6500-types:STRING;
          description
            "Reach Specification";
        }
        leaf est-length {
          yang:get-supported "true";
          type ciena-6500-types:STRING;
          description
            "Estimated fiber length";
        }
        leaf rtd {
          yang:get-supported "true";
          type ciena-6500-types:STRING;
          description
            "OCH Round Trip Delay.";
        }
        leaf uni-latency {
          yang:get-supported "true";
          type ciena-6500-types:STRING;
          description
            "OCH Unidirectional Latency.";
        }
        leaf rx-echo-trace {
          yang:get-supported "true";
          type ciena-6500-types:STRING;
          description
            "TR Transmit Identifier Received";
        }
        leaf tx-trace {
          yang:get-supported "true";
          type ciena-6500-types:STRING;
          description
            "TR Transmit Identifier Received Expected";
        }
        leaf tx-assoc-far-end-rx {
          yang:get-supported "true";
          type ciena-6500-types:STRING;
          description
            "Transmitter associated far end receiver";
        }
        leaf port-mode {
          yang:get-supported "true";
          type enumeration {
            enum SONET;
            enum SDH;
          }
          description
            "Optical port Market preference";
        }
        leaf tf-mode {
          yang:get-supported "true";
          type enumeration {
            enum OFF {
              description
                "Alarms off, no traffic protection";
            }
            enum ALMONLY {
              description
                "Alarms on, no traffic protection";
            }
          }
          description
            "OTU Trace Fail Mode";
        }
        leaf odu-tf-mode {
          yang:get-supported "true";
          type enumeration {
            enum OFF {
              description
                "Alarms off, no traffic protection";
            }
            enum ALMONLY {
              description
                "Alarms on, no traffic protection";
            }
          }
          description
            "ODU Trace Fail Mode";
        }
        leaf otu-timen {
          yang:get-supported "true";
          type enumeration {
            enum OPERATOR {
              description
                "Monitor OTU Operator Specific TTI mismatch";
            }
            enum SAPI {
              description
                "Monitor OTU SAPI TTI mismatch";
            }
            enum DAPI {
              description
                "Monitor OTU DAPI TTI mismatch";
            }
            enum SAPI_DAPI {
              description
                "Monitor OTU SAPI and DAPI TTI mismatch";
            }
          }
          description
            "OTU TTI Mismatch Detection";
        }
        leaf odu-timen {
          yang:get-supported "true";
          type enumeration {
            enum OPERATOR {
              description
                "Monitor ODU Operator Specific TTI mismatch";
            }
            enum SAPI {
              description
                "Monitor ODU SAPI TTI mismatch";
            }
            enum DAPI {
              description
                "Monitor ODU DAPI TTI mismatch";
            }
            enum SAPI_DAPI {
              description
                "Monitor ODU SAPI and DAPI TTI mismatch";
            }
          }
          description
            "ODU TTI Mismatch Detection";
        }
        leaf odu-monitor {
          yang:get-supported "true";
          type enumeration {
            enum NO {
              description
                "ODU Monitoring off";
            }
            enum YES {
              description
                "ODU Monitoring on";
            }
          }
          description
            "ODU Monitor";
        }
        leaf pre-fec-sf-th-lev {
          yang:get-supported "true";
          type ciena-6500-types:STRING;
          description
            "Pre-FEC Signal Fail Threshold Level (decimal value in dbQ). Parameter applies when FEC is ON";
        }
        leaf otu-sd-th-lev {
          yang:get-supported "true";
          type ciena-6500-types:INT;
          description
            "OTU Signal Degrade Threshold Level, only applies when FEC is OFF";
        }
        leaf odu-sf-th-lev {
          default "0";
          yang:get-supported "true";
          type ciena-6500-types:INT;
          description
            "ODU Post-FEC Signal Fail Threshold Level";
        }
        leaf odu-sd-th-lev {
          default "0";
          yang:get-supported "true";
          type ciena-6500-types:INT;
          description
            "ODU Post-FEC Signal Degrade Threshold Level";
        }
        leaf exp-pt {
          yang:get-supported "true";
          type ciena-6500-types:STRING;
          description
            "HEX value in the range 0x00-0xFF. This attribute is used to specify the value of Expected PT.";
        }
        leaf tx-pt {
          yang:get-supported "true";
          type ciena-6500-types:STRING;
          description
            "HEX value in the range 0x00-0xFF. This attribute is used to specify the value of Transmitted PT.";
        }
        leaf pre-fec-sf-th-ber {
          yang:get-supported "true";
          type ciena-6500-types:STRING;
          description
            "Pre-FEC Signal Fail Threshold Bit Error Rate. Parameter applies when FEC is ON";
        }
        leaf pre-fec-sd-th-lev {
          yang:get-supported "true";
          type ciena-6500-types:STRING;
          description
            "Pre-FEC Signal Degrade Threshold Level (decimal value in dbQ). Parameter applies when FEC is ON";
        }
        leaf pre-fec-sd-th-ber {
          yang:get-supported "true";
          type ciena-6500-types:STRING;
          description
            "Pre-FEC Signal Degrade Threshold Bit Error Rate. Parameter applies when FEC is ON";
        }
        leaf otu-rate {
          yang:get-supported "true";
          type enumeration {
            enum 44G5 {
              description
                "44.5 G connection - Typically OTU3 Mapping";
            }
            enum 43G018 {
              description
                "43.018 G connection - Typically OTU3 40G rate";
            }
          }
          description
            "OTMn Rate";
        }
        leaf ains-time-left {
          yang:get-supported "true";
          type ciena-6500-types:TIME;
          description
            "The format will be \"HH-MM\" for the time left in AINS timeout.";
        }
        leaf otm-term {
          yang:get-supported "true";
          type ciena-6500-types:STRING;
          description
            "OTM Termination per layer (OPU and/or ODU and/or OTU)";
        }
        leaf otm-flt-mon {
          yang:get-supported "true";
          type ciena-6500-types:STRING;
          description
            "OTM Fault Monitoring per layer (OPU and/or ODU and/or OTU)";
        }
        leaf otm-prf-mon {
          yang:get-supported "true";
          type ciena-6500-types:STRING;
          description
            "OTM Performance Monitoring per layer (OPU and/or ODU and/or OTU)";
        }
        leaf odu-handoff {
          yang:get-supported "true";
          type enumeration {
            enum AUTO {
              description
                "Automatic Mapping";
            }
            enum ODU3 {
              description
                "ODU3 Mapping";
            }
            enum OC768 {
              description
                "OC768 Mapping";
            }
            enum ETH40G {
              description
                "ETH40G Mapping";
            }
            enum 4X10G1 {
              description
                "4X10G Mapping Mode 1";
            }
            enum 4X10G2 {
              description
                "4X10G Mapping Mode 2";
            }
            enum 4X10G3 {
              description
                "4X10G Mapping Mode 3";
            }
            enum 4X10G4 {
              description
                "4X10G Mapping Mode 4";
            }
            enum 4X10G5 {
              description
                "4X10G Mapping Mode 5";
            }
            enum 4X10G6 {
              description
                "4X10G Mapping Mode 6";
            }
          }
          description
            "ODU Handoff Mapping Mode";
        }
        leaf line-type {
          yang:get-supported "true";
          type ciena-6500-enums:linetype;
          description
            "OCH Line Sys Type";
        }
        leaf clfi {
          yang:get-supported "true";
          type ciena-6500-types:STRING;
          description
            "Common Language Facility Identifier.Customer provisionable label for a facility.";
        }
        leaf cond-type {
          yang:get-supported "true";
          type ciena-6500-enums:OTM_CONDTYPE;
          description
            "The type of conditioning";
        }
        leaf laser-off-far-end-fail {
          yang:get-supported "true";
          type ciena-6500-enums:Laserofffarendfail;
          description
            "Enabled or Disabled LOL (Loss of Light) feature";
        }
        leaf frr {
          yang:get-supported "true";
          type enumeration {
            enum DISABLED {
              description
                "DISABLED Mode";
            }
            enum ENABLED {
              description
                "ENABLED Mode";
            }
          }
          description
            "OCH Fast Receiver Recovery";
        }
        leaf frr-config {
          yang:get-supported "true";
          type enumeration {
            enum MATCHEDCD {
              description
                "Matched Chromatic Dispersion";
            }
            enum DIVERSECD2 {
              description
                "Diverse Chromatic Dispersion 2 Paths";
            }
          }
          description
            "OCH FRR Network Configuration";
        }
        leaf frr-path1-disp {
          yang:get-supported "true";
          type ciena-6500-types:STRING;
          description
            "OCH FRR Link Dispersion for Path 1";
        }
        leaf frr-path2-disp {
          yang:get-supported "true";
          type ciena-6500-types:STRING;
          description
            "OCH FRR Link Dispersion for Path 2";
        }
        leaf dm-enable {
          yang:get-supported "true";
          type enumeration {
            enum YES {
              description
                "Delay measurement is enabled.";
            }
            enum NO {
              description
                "Delay measurement is disabled.";
            }
          }
          description
            "Indicates whether delay measurement is enabled or disabled.";
        }
        leaf dm-count {
          yang:get-supported "true";
          type ciena-6500-types:STRING;
          description
            "Most recent delay measurement count.";
        }
        leaf hold-off {
          default "0";
          yang:get-supported "true";
          type ciena-6500-types:INT;
          description
            "HoldOff signal conditioning timer";
        }
        leaf hold-on {
          default "0";
          yang:get-supported "true";
          type ciena-6500-types:INT;
          description
            "HoldOn signal conditioning timer";
        }
        leaf spli-mgmt {
          yang:get-supported "true";
          type ciena-6500-enums:spliMgmt;
          description
            "Identify if Port is Manageable by SPLI";
        }
        leaf crs-rate {
          yang:get-supported "true";
          type enumeration {
            enum NIL {
              description
                "crsRate is not supported";
            }
            enum 4XODU2E {
              description
                "The connection rate is 4XODU2E";
            }
            enum ODU3 {
              description
                "The connection rate is ODU3";
            }
          }
          description
            "ODU connection rate";
        }
        leaf spli-managed {
          yang:get-supported "true";
          type ciena-6500-enums:spliManaged;
          description
            "Identify if Port is Currently Managed by SPLI";
        }
        leaf pst {
          yang:get-supported "true";
          type ciena-6500-enums:PSTfac_RTRV;
          description
            "Identify the primary State";
        }
        leaf-list sst {
          yang:get-supported "true";
          type enumeration {
            enum AINS {
              description
                "Auto-In-Service";
            }
            enum MT {
              description
                "Maintenance";
            }
            enum FLT {
              description
                "Fault detected";
            }
            enum SGEO {
              description
                "Supporting Entity Outage (based on PSTQ of OOS-AU, OOS-AUMA only)";
            }
            enum LPBK {
              description
                "Loopback";
            }
            enum DISCD {
              description
                "Disconnected. (no transparent traffic connection on this facility)";
            }
            enum TSGEN {
              description
                "Test set generation";
            }
            enum TSMON {
              description
                "Test set monitor";
            }
            enum WRKRX {
              description
                "Active OTM3 Facility in Receiving Direction (in protection configuration only)";
            }
            enum WRKTX {
              description
                "Active OTM3 Facility in Transmitting Direction (in protection configuration only)";
            }
            enum STBYH {
              description
                "Hot Standby (in protection configuration only)";
            }
            enum PSI {
              description
                "Protection Switch Inhibited (in protection configuration only)";
            }
          }
          description
            "Secondary State";
        }
      }
    }
  }

  rpc port-disable-otm3 {
    description
      "Remove an OTM3 Facility";
    yang:handler "tl1";
    input {
      leaf otm3aid {
        mandatory true;
        description
          "AID in format OTM3-shelf-slot-port";
        type ciena-6500-types:aid;
      }
      leaf sst {
        type ciena-6500-enums:RMVSSTMT;
        description
          "Identify Maintenance State";
      }
    }
  }

  rpc port-enable-otm3 {
    description
      "Restore an OTM3 Facility";
    yang:handler "tl1";
    input {
      leaf otm3aid {
        mandatory true;
        description
          "AID in format OTM3-shelf-slot-port";
        type ciena-6500-types:aid;
      }
    }
  }

  rpc port-show-otminfo {
    description
      "Retrieve parameters against the OTMn Facility";
    yang:handler "tl1";
    input {
      leaf otmnaid {
        mandatory true;
        description
          "AID in format OTM2-shelf-slot-port, OTM2-shelf-slot-portSsubport, OTM3-shelf-slot-port, OTM4-shelf-slot-port, OTM0-shelf-slot-port, OTM1-shelf-slot-port, OTMFLEX-shelf-slot-port";
        type ciena-6500-types:aid;
      }
    }
    output {
      list output {
        leaf otmnaid {
          yang:get-supported "true";
          type ciena-6500-types:IDENT;
          description
            "aid";
        }
        leaf otu-rate-rx {
          yang:get-supported "true";
          type enumeration {
            enum 10G709 {
              description
                "10.70 G connection";
            }
            enum 11G05 {
              description
                "11.05 G connection";
            }
            enum 11G09 {
              description
                "11.09 G connection";
            }
            enum 112G {
              description
                "112 G connection";
            }
            enum UNAVAILABLE {
              description
                "Not Retreivable, Circuit pack missing or not ready";
            }
            enum UNKNOWN {
              description
                "Not Retreivable, Circuit pack cannot retrieve value";
            }
          }
          description
            "RX OTU Rate";
        }
        leaf received-pt {
          yang:get-supported "true";
          type ciena-6500-types:STRING;
          description
            "Received Payload Type. HEX value in the range 0x00-0xFF";
        }
      }
    }
  }

  rpc port-show-otm {
    description
      "Retrieve parameters against the OTM Facility";
    yang:handler "tl1";
    input {
      leaf otmaid {
        mandatory true;
        description
          "AID in format OTM1-shelf-slot-port, OTM4-shelf-slot-port, OTMC2-shelf-slot-port, OTM-shelf-slot-port, OTM0-shelf-slot-port, OTMFLEX-shelf-slot-port";
        type ciena-6500-types:aid;
      }
      leaf tti-info {
        yang:get-supported "true";
        type enumeration {
          enum NO {
            description
              "Do not include TTI information in the response";
          }
          enum YES {
            description
              "Include TTI information in the response";
          }
        }
        description
          "Specify if TTI Information is to be included in the response (default is NO).";
      }
      leaf stats-info {
        yang:get-supported "true";
        type enumeration {
          enum NO {
            description
              "Do not include Dynamic Status information in the response";
          }
          enum YES {
            description
              "Include Dynamic Status information in the response";
          }
        }
        description
          "Specify if Dynamic Status Information is to be included in the response (default is YES).";
      }
      leaf otm-flags {
        yang:get-supported "true";
        type enumeration {
          enum NO {
            description
              "Do not include detailed OTM (OTU, OPU, ODU) termination and monitoring information in the response";
          }
          enum YES {
            description
              "Include detailed OTM (OTU, OPU, ODU) termination and monitoring in the response";
          }
        }
        description
          "Specify if OTM (OPU, ODU, OTU) Layer termination and monitoring indicators are to be included in the response (default is NO).";
      }
      leaf disp-scan-info {
        yang:get-supported "true";
        type enumeration {
          enum YES {
            description
              "Do not include SFROM,STO, SSTEP, SDWELL, SCAN, OCHTXDISPFOUND and OCHASSOCQ in the response";
          }
          enum NO {
            description
              "Include SFROM,STO, SSTEP, SDWELL, SCAN, OCHTXDISPFOUND and OCHASSOCQ in the response";
          }
        }
        description
          "Indicates whether to include SFROM,STO, SSTEP, SDWELL, SCAN, OCHASSOCQ, OCHTXDISPFOUND in the response";
      }
    }
    output {
      list output {
        leaf otmaid {
          yang:get-supported "true";
          type ciena-6500-types:IDENT;
          description
            "aid";
        }
        leaf osid {
          yang:get-supported "true";
          type string {
            length "0..8";
          }
          description
            "8 Byte OSID identifier";
        }
        leaf tx-fec-frmt {
          yang:get-supported "true";
          type enumeration {
            enum OFF {
              description
                "NO FEC";
            }
            enum RS8 {
              description
                "Reed Solomon 8";
            }
            enum PFEC {
              description
                "Product FEC";
            }
            enum QFEC {
              description
                "QFEC";
            }
          }
          description
            "TX Supported FEC";
        }
        leaf rx-fec-frmt {
          yang:get-supported "true";
          type enumeration {
            enum OFF {
              description
                "NO FEC";
            }
            enum RS8 {
              description
                "Reed Solomon 8";
            }
            enum PFEC {
              description
                "Product FEC";
            }
            enum QFEC {
              description
                "QFEC";
            }
          }
          description
            "RX Supported FEC";
        }
        leaf odu-term {
          yang:get-supported "true";
          type enumeration {
            enum YES {
              description
                "Indicates that ODU TTI is terminated on this OTM facility.";
            }
            enum NO {
              description
                "Indicates that ODU TTI is not terminated on this OTM facility.";
            }
          }
          description
            "ODUTTITERM parameter values indicate:?YES?: means that ODU TTI is terminated on this particular OTM facility and Site Manager should display ODU TTI and allow provisioning / monitoring of all ODU TTI parameters.?NO?: means that ODU TTI is not terminated on this port and SM should not display the ODU TTI parameters except the ODU TTI RX Incoming value. The 6500 BB circuit packs that act as regen will passthrough ODU TTI but will allow for the monitoring of ODU TTI RX Incoming value.When there is no client facility, ODU TTI is not terminated. Default is NO since the client facility does not autoprov. If client facility is not an OTM, then this port terminates ODU TTI (Terminal). If client facility is OTM, then this port does not terminate ODU TTI (Regen).";
        }
        leaf otu-tx-tti {
          yang:get-supported "true";
          type ciena-6500-types:STRING;
          description
            "Transmitted TTI 32B. TTI =OTU Trail Trace Identifier";
        }
        leaf odu-tx-tti {
          yang:get-supported "true";
          type ciena-6500-types:STRING;
          description
            "Transmitted TTI 32B. TTI =ODU Trail Trace Identifier";
        }
        leaf otu-rx-exp-tti {
          yang:get-supported "true";
          type ciena-6500-types:STRING;
          description
            "Expected 32 Characters OTU TTI";
        }
        leaf odu-rx-exp-tti {
          yang:get-supported "true";
          type ciena-6500-types:STRING;
          description
            "Expected 32 Characters ODU TTI";
        }
        leaf otu-tx-sapi {
          yang:get-supported "true";
          type ciena-6500-types:STRING;
          description
            "OTU Transmitted SAPI TTI (15 Characters). TTI = Trail Trace Identifier";
        }
        leaf otu-tx-dapi {
          yang:get-supported "true";
          type ciena-6500-types:STRING;
          description
            "OTU Transmitted DAPI TTI (15 Characters). TTI = Trail Trace Identifier";
        }
        leaf otu-exp-sapi {
          yang:get-supported "true";
          type ciena-6500-types:STRING;
          description
            "OTU Expected SAPI TTI (15 Characters)";
        }
        leaf otu-exp-dapi {
          yang:get-supported "true";
          type ciena-6500-types:STRING;
          description
            "OTU Expected DAPI TTI (15 Characters)";
        }
        leaf odu-tx-sapi {
          yang:get-supported "true";
          type ciena-6500-types:STRING;
          description
            "ODU Transmitted SAPI TTI (15 Characters). TTI = Trail Trace Identifier";
        }
        leaf odu-tx-dapi {
          yang:get-supported "true";
          type ciena-6500-types:STRING;
          description
            "ODU Transmitted DAPI TTI (15 Characters). TTI = Trail Trace Identifier";
        }
        leaf odu-exp-sapi {
          yang:get-supported "true";
          type ciena-6500-types:STRING;
          description
            "ODU Expected SAPI TTI (15 Characters)";
        }
        leaf odu-exp-dapi {
          yang:get-supported "true";
          type ciena-6500-types:STRING;
          description
            "ODU Expected DAPI TTI (15 Characters)";
        }
        leaf tx-path-id {
          default "1";
          yang:get-supported "true";
          type ciena-6500-types:INT {
            range "1..254";
          }
          description
            "TX path identifier";
        }
        leaf tx-mode {
          yang:get-supported "true";
          type enumeration {
            enum MANUAL {
              description
                "Manual Precompensation Mode";
            }
            enum AUTOMATIC {
              description
                "Automatic Precompensation Mode";
            }
            enum CUSTOM1 {
              description
                "Custom1 Precompensation Mode";
            }
            enum OFF {
              description
                "No Precompensation Mode";
            }
            enum OFFSETAUTO {
              description
                "Offset Automatic Precompensation Mode";
            }
            enum EXTENDEDMANUAL {
              description
                "Extended Manual Precompensation Mode";
            }
          }
          description
            "Transmitter Dispersion Mode";
        }
        leaf tx-disp-prov {
          yang:get-supported "true";
          type ciena-6500-types:INT;
          description
            "Transmitter Dispersion Provisioned Value";
        }
        leaf tx-act-disp {
          yang:get-supported "true";
          type union {
            type enumeration {
              enum UNKNOWN;
            }
            type ciena-6500-types:INT;
          }
          description
            "Transmitter total actual link dispersion in the near-to-far direction";
        }
        leaf tx-disp-min {
          yang:get-supported "true";
          type ciena-6500-types:INT;
          description
            "Minimum Transmitter Dispersion Value";
        }
        leaf tx-disp-max {
          yang:get-supported "true";
          type ciena-6500-types:INT;
          description
            "Maximum Transmitter Dispersion Value";
        }
        leaf rx-act-disp {
          yang:get-supported "true";
          type union {
            type enumeration {
              enum UNKNOWN;
            }
            type ciena-6500-types:INT;
          }
          description
            "Receiver total actual link dispersion in the far-to-near direction";
        }
        leaf tx-pre-disp {
          yang:get-supported "true";
          type union {
            type enumeration {
              enum UNKNOWN;
            }
            type ciena-6500-types:INT;
          }
          description
            "Tx Precompensation Dispersion Value.";
        }
        leaf rx-post-disp {
          yang:get-supported "true";
          type union {
            type enumeration {
              enum UNKNOWN;
            }
            type ciena-6500-types:INT;
          }
          description
            "Rx Postcompensation Dispersion Value.";
        }
        leaf rotation {
          yang:get-supported "true";
          type enumeration {
            enum DISABLED {
              description
                "Disabled OCH Jones Rotation feature ";
            }
            enum ENABLED {
              description
                "Enabled OCH Jones Rotation feature";
            }
          }
          description
            "OCH Jones Rotation feature";
        }
        leaf tx-pwr {
          yang:get-supported "true";
          type ciena-6500-types:STRING;
          description
            "Provisioned TX Power in dBm (xx.x)";
        }
        leaf tx-act-pwr {
          yang:get-supported "true";
          type ciena-6500-types:STRING;
          description
            "TX actual power in dBm (xx.x)";
        }
        leaf tx-min-pwr {
          yang:get-supported "true";
          type ciena-6500-types:STRING;
          description
            "TX minimum power in dBm (xx.x)";
        }
        leaf tx-max-pwr {
          yang:get-supported "true";
          type ciena-6500-types:STRING;
          description
            "TX maximum power in dBm (xx.x)";
        }
        leaf rx-act-pwr {
          yang:get-supported "true";
          type ciena-6500-types:STRING;
          description
            "RX actual power in dBm (xx.x)";
        }
        leaf rx-min-pwr {
          yang:get-supported "true";
          type ciena-6500-types:STRING;
          description
            "RX minimum power in dBm (xx.x)";
        }
        leaf rx-max-pwr {
          yang:get-supported "true";
          type ciena-6500-types:STRING;
          description
            "RX maximum power in dBm (xx.x)";
        }
        leaf rx-ch-act-pwr {
          yang:get-supported "true";
          type ciena-6500-types:STRING;
          description
            "RX channel actual power in dBm (xx.x)";
        }
        leaf rx-ch-min-pwr {
          yang:get-supported "true";
          type ciena-6500-types:STRING;
          description
            "RX channel minimum power in dBm (xx.x)";
        }
        leaf rx-ch-max-pwr {
          yang:get-supported "true";
          type ciena-6500-types:STRING;
          description
            "RX channel maximum power in dBm (xx.x)";
        }
        leaf pwr-bal-ctlr {
          yang:get-supported "true";
          type enumeration {
            enum DISABLED {
              description
                "Power Balance Controller Disabled";
            }
            enum ENABLED {
              description
                "Power Balance Controller Enabled";
            }
          }
          description
            "Provisioned Power Balance Controller Operating Mode";
        }
        leaf pwr-bal-offset {
          yang:get-supported "true";
          type ciena-6500-types:STRING;
          description
            "Provisioned Power Balance Offset in dB (xx.x)";
        }
        leaf pwr-bal-act-offset {
          yang:get-supported "true";
          type ciena-6500-types:STRING;
          description
            "Provisioned Power Balance Actual Offset in dB (xx.x)";
        }
        leaf tx-act-high-pwr {
          yang:get-supported "true";
          type ciena-6500-types:STRING;
          description
            "TX Actual High Power Value in dBm (xx.x)";
        }
        leaf tx-act-low-pwr {
          yang:get-supported "true";
          type ciena-6500-types:STRING;
          description
            "TX Actual Low Power Value in dBm (xx.x)";
        }
        leaf rx-act-high-pwr {
          yang:get-supported "true";
          type ciena-6500-types:STRING;
          description
            "RX Actual High Power Value in dBm (xx.x)";
        }
        leaf rx-act-low-pwr {
          yang:get-supported "true";
          type ciena-6500-types:STRING;
          description
            "RX Actual Low Power Value in dBm (xx.x)";
        }
        leaf-list tx-act-ln-pwr {
          yang:get-supported "true";
          type ciena-6500-types:STRING;
          description
            "Lane TX Power Value in dBm (xx.x)";
        }
        leaf-list rx-act-ln-pwr {
          yang:get-supported "true";
          type ciena-6500-types:STRING;
          description
            "Lane RX Power Value in dBm (xx.x)";
        }
        leaf tx-wvlngth-prov {
          yang:get-supported "true";
          type ciena-6500-types:STRING;
          description
            "Provisioned Wavelength in nm (xxxx.xx)";
        }
        leaf tx-wvlngth-min {
          default "0.00";
          yang:get-supported "true";
          type ciena-6500-types:STRING;
          description
            "Minimum Wavelength value in nm (xxxx.xx)";
        }
        leaf tx-wvlngth-max {
          default "0.00";
          yang:get-supported "true";
          type ciena-6500-types:STRING;
          description
            "Maximum Wavelength value in nm (xxxx.xx)";
        }
        leaf tx-wvlngth-spacing {
          yang:get-supported "true";
          type enumeration {
            enum 50 {
              description
                "50GHz";
            }
            enum FLEXGRID {
              description
                "FLEXGRID";
            }
          }
          description
            "OCH Wavelength Spacing";
        }
        leaf differential-encoding {
          yang:get-supported "true";
          type enumeration {
            enum NONE {
              description
                "TR Control NONE";
            }
            enum HARD {
              description
                "TR Control HARD";
            }
            enum SOFT {
              description
                "TR Control SOFT";
            }
            enum XD {
              description
                "TR Control XD";
            }
          }
          description
            "OCH Differential Encoding";
        }
        leaf spectral-occupancy {
          yang:get-supported "true";
          type enumeration {
            enum NONE;
            enum NARROW;
            enum WIDE20;
            enum WIDE25;
            enum WIDE30;
            enum WIDE40;
            enum WIDE50;
            enum MINSPACE20;
            enum MINSPACE25;
          }
          description
            "OCH Spectral Occupancy setting";
        }
        leaf odu-handoff {
          yang:get-supported "true";
          type enumeration {
            enum AUTO {
              description
                "Automatic Mapping";
            }
            enum ODU3 {
              description
                "ODU3 Mapping";
            }
            enum OC768 {
              description
                "OC768 Mapping";
            }
            enum ETH40G {
              description
                "ETH40G Mapping";
            }
            enum 4X10G1 {
              description
                "4X10G Mapping Mode 1";
            }
            enum 4X10G2 {
              description
                "4X10G Mapping Mode 2";
            }
            enum 4X10G3 {
              description
                "4X10G Mapping Mode 3";
            }
            enum 4X10G4 {
              description
                "4X10G Mapping Mode 4";
            }
            enum 4X10G5 {
              description
                "4X10G Mapping Mode 5";
            }
            enum 4X10G6 {
              description
                "4X10G Mapping Mode 6";
            }
            enum HALFODUALIGN {
              description
                "Master Slave - Half ODU Align Mapping Mode";
            }
          }
          description
            "ODU Handoff Mapping Mode";
        }
        leaf tuning-mode {
          yang:get-supported "true";
          type enumeration {
            enum NORMAL {
              description
                "Normal Tuning Mode";
            }
            enum ACCELERATED {
              description
                "Accelerated Tuning Mode";
            }
            enum FAST {
              description
                "Fast Tuning Mode";
            }
          }
          description
            "Provisioned Tuning Mode";
        }
        leaf optimize-mode {
          yang:get-supported "true";
          type ciena-6500-enums:optimizeMode;
          description
            "Performance Optimization Mode";
        }
        leaf max-pmd {
          yang:get-supported "true";
          type ciena-6500-types:STRING;
          description
            "Supported Mean DGD (Differential Group Delay) value";
        }
        leaf rx-act-pmd {
          yang:get-supported "true";
          type ciena-6500-types:STRING;
          description
            "Estimated Instance of DGD (Differential Group Delay) value";
        }
        leaf reach-spec {
          yang:get-supported "true";
          type ciena-6500-types:STRING;
          description
            "Reach Specification";
        }
        leaf est-length {
          yang:get-supported "true";
          type ciena-6500-types:STRING;
          description
            "Estimated fiber length";
        }
        leaf rtd {
          yang:get-supported "true";
          type ciena-6500-types:STRING;
          description
            "OCH Round Trip Delay.";
        }
        leaf uni-latency {
          yang:get-supported "true";
          type ciena-6500-types:STRING;
          description
            "OCH Unidirectional Latency.";
        }
        leaf rx-echo-trace {
          yang:get-supported "true";
          type ciena-6500-types:STRING;
          description
            "TR Transmit Identifier Received";
        }
        leaf tx-trace {
          yang:get-supported "true";
          type ciena-6500-types:STRING;
          description
            "TR Transmit Identifier Received Expected";
        }
        leaf tx-assoc-far-end-rx {
          yang:get-supported "true";
          type ciena-6500-types:STRING;
          description
            "Transmitter associated far end receiver";
        }
        leaf port-mode {
          yang:get-supported "true";
          type enumeration {
            enum SONET;
            enum SDH;
          }
          description
            "Optical port Market preference";
        }
        leaf tf-mode {
          yang:get-supported "true";
          type enumeration {
            enum OFF {
              description
                "Alarms off, no traffic protection";
            }
            enum ALMONLY {
              description
                "Alarms on, no traffic protection";
            }
          }
          description
            "OTU Trace Fail Mode";
        }
        leaf odu-tf-mode {
          yang:get-supported "true";
          type enumeration {
            enum OFF {
              description
                "Alarms off, no traffic protection";
            }
            enum ALMONLY {
              description
                "Alarms on, no traffic protection";
            }
          }
          description
            "ODU Trace Fail Mode";
        }
        leaf otu-timen {
          yang:get-supported "true";
          type enumeration {
            enum OPERATOR {
              description
                "Monitor OTU Operator Specific TTI mismatch";
            }
            enum SAPI {
              description
                "Monitor OTU SAPI TTI mismatch";
            }
            enum DAPI {
              description
                "Monitor OTU DAPI TTI mismatch";
            }
            enum SAPI_DAPI {
              description
                "Monitor OTU SAPI and DAPI TTI mismatch";
            }
          }
          description
            "OTU TTI Mismatch Detection";
        }
        leaf odu-timen {
          yang:get-supported "true";
          type enumeration {
            enum OPERATOR {
              description
                "Monitor ODU Operator Specific TTI mismatch";
            }
            enum SAPI {
              description
                "Monitor ODU SAPI TTI mismatch";
            }
            enum DAPI {
              description
                "Monitor ODU DAPI TTI mismatch";
            }
            enum SAPI_DAPI {
              description
                "Monitor ODU SAPI and DAPI TTI mismatch";
            }
          }
          description
            "ODU TTI Mismatch Detection";
        }
        leaf laser-off-far-end-fail {
          yang:get-supported "true";
          type ciena-6500-enums:Laserofffarendfail;
          description
            "Enabled or Disabled LOL (Loss of Light) feature";
        }
        leaf tx-chrip {
          yang:get-supported "true";
          type enumeration {
            enum POSITIVE;
            enum NEGATIVE;
          }
          description
            "Positive or Negative Chirp setting";
        }
        leaf frr {
          yang:get-supported "true";
          type enumeration {
            enum DISABLED {
              description
                "DISABLED Mode";
            }
            enum ENABLED {
              description
                "ENABLED Mode";
            }
          }
          description
            "OCH Fast Receiver Recovery";
        }
        leaf frr-config {
          yang:get-supported "true";
          type enumeration {
            enum MATCHEDCD {
              description
                "Matched Chromatic Dispersion";
            }
            enum DIVERSECD2 {
              description
                "Diverse Chromatic Dispersion 2 Paths";
            }
          }
          description
            "OCH FRR Network Configuration";
        }
        leaf frr-path1-disp {
          yang:get-supported "true";
          type ciena-6500-types:STRING;
          description
            "OCH FRR Link Dispersion for Path 1";
        }
        leaf frr-path2-disp {
          yang:get-supported "true";
          type ciena-6500-types:STRING;
          description
            "OCH FRR Link Dispersion for Path 2";
        }
        leaf odu-monitor {
          yang:get-supported "true";
          type enumeration {
            enum NO {
              description
                "ODU Monitoring off";
            }
            enum YES {
              description
                "ODU Monitoring on";
            }
          }
          description
            "ODU Monitor";
        }
        leaf pre-fec-sf-th-lev {
          yang:get-supported "true";
          type ciena-6500-types:STRING;
          description
            "Pre-FEC Signal Fail Threshold Level (decimal value in dbQ). Parameter applies when FEC is ON";
        }
        leaf pre-fec-sf-th-ber {
          yang:get-supported "true";
          type ciena-6500-types:STRING;
          description
            "Pre-FEC Signal Fail Threshold Bit Error Rate. Parameter applies when FEC is ON";
        }
        leaf pre-fec-sd-th-lev {
          yang:get-supported "true";
          type ciena-6500-types:STRING;
          description
            "Pre-FEC Signal Degrade Threshold Level (decimal value in dbQ). Parameter applies when FEC is ON";
        }
        leaf pre-fec-sd-th-ber {
          yang:get-supported "true";
          type ciena-6500-types:STRING;
          description
            "Pre-FEC Signal Degrade Threshold Bit Error Rate. Parameter applies when FEC is ON";
        }
        leaf otu-sd-th-lev {
          yang:get-supported "true";
          type ciena-6500-types:INT;
          description
            "OTU Signal Degrade Threshold Level, only applies when FEC is OFF";
        }
        leaf odu-sf-th-lev {
          default "0";
          yang:get-supported "true";
          type ciena-6500-types:INT;
          description
            "ODU Post-FEC Signal Fail Threshold Level";
        }
        leaf odu-sd-th-lev {
          default "0";
          yang:get-supported "true";
          type ciena-6500-types:INT;
          description
            "ODU Post-FEC Signal Degrade Threshold Level";
        }
        leaf otu-rate {
          yang:get-supported "true";
          type enumeration {
            enum 1G244 {
              description
                "1.244 G connection - OTM0";
            }
            enum 2G7 {
              description
                "2.7 G connection - OTM1";
            }
            enum 5G02 {
              description
                "5.02 G connection - OTMFLEX";
            }
            enum 112G {
              description
                "112 G connection - Typically OTU4 Mapping";
            }
            enum OTUC4-60 {
              description
                "OTUC4-60 Rate connection";
            }
            enum 2xOTU4 {
              description
                "2 x OTU4(112G) Rate connection";
            }
          }
          description
            "OTMn Rate";
        }
        leaf exp-pt {
          yang:get-supported "true";
          type ciena-6500-types:STRING;
          description
            "HEX value in the range 0x00-0xFF. This attribute is used to specify the value of Expected PT.";
        }
        leaf tx-pt {
          yang:get-supported "true";
          type ciena-6500-types:STRING;
          description
            "HEX value in the range 0x00-0xFF. This attribute is used to specify the value of Transmitted PT.";
        }
        leaf otm-term {
          yang:get-supported "true";
          type ciena-6500-types:STRING;
          description
            "OTM Termination per layer (OPU and/or ODU and/or OTU)";
        }
        leaf ains-time-left {
          yang:get-supported "true";
          type ciena-6500-types:TIME;
          description
            "The format will be \"HH-MM\" for the time left in AINS timeout.";
        }
        leaf otm-flt-mon {
          yang:get-supported "true";
          type ciena-6500-types:STRING;
          description
            "OTM Fault Monitoring per layer (OPU and/or ODU and/or OTU)";
        }
        leaf otm-prf-mon {
          yang:get-supported "true";
          type ciena-6500-types:STRING;
          description
            "OTM Performance Monitoring per layer (OPU and/or ODU and/or OTU)";
        }
        leaf cond-type {
          yang:get-supported "true";
          type ciena-6500-enums:OTM_CONDTYPE;
          description
            "The type of conditioning";
        }
        leaf line-type {
          yang:get-supported "true";
          type ciena-6500-enums:linetype;
          description
            "OCH Line Sys Type";
        }
        leaf clfi {
          yang:get-supported "true";
          type ciena-6500-types:STRING;
          description
            "Common Language Facility Identifier.Customer provisionable label for a facility.";
        }
        leaf dm-enable {
          yang:get-supported "true";
          type enumeration {
            enum YES {
              description
                "Delay measurement is enabled.";
            }
            enum NO {
              description
                "Delay measurement is disabled.";
            }
          }
          description
            "Indicates whether delay measurement is enabled or disabled.";
        }
        leaf dm-count {
          yang:get-supported "true";
          type ciena-6500-types:STRING;
          description
            "Most recent delay measurement count.";
        }
        leaf hold-off {
          default "0";
          yang:get-supported "true";
          type ciena-6500-types:INT;
          description
            "HoldOff signal conditioning timer";
        }
        leaf hold-on {
          default "0";
          yang:get-supported "true";
          type ciena-6500-types:INT;
          description
            "HoldOn signal conditioning timer";
        }
        leaf tx-disp-found {
          yang:get-supported "true";
          type union {
            type enumeration {
              enum UNKNOWN;
            }
            type ciena-6500-types:INT;
          }
          description
            "Found the optimum Pre-dispersion compensation from the scanning, ps/nm";
        }
        leaf assoc-q {
          yang:get-supported "true";
          type union {
            type enumeration {
              enum UNKNOWN;
            }
            type ciena-6500-types:INT;
          }
          description
            "Q associated with the found optimum precomp";
        }
        leaf scan {
          yang:get-supported "true";
          type enumeration {
            enum START {
              description
                "Triggers Q-based Pre-dispersion compensation Scanning";
            }
            enum STOP {
              description
                "Cancels Q-based Pre-dispersion compensation Scanning";
            }
            enum COMPLETE {
              description
                "Indicates completion of Scanning, only for RTRV ";
            }
          }
          description
            "Q-based Pre-dispersion compensation Scanning";
        }
        leaf s-from {
          yang:get-supported "true";
          type ciena-6500-types:INT;
          description
            "FROM point of scanning range, ps/nm";
        }
        leaf s-to {
          yang:get-supported "true";
          type ciena-6500-types:INT;
          description
            "TO point of scanning range, ps/nm";
        }
        leaf s-step {
          yang:get-supported "true";
          type ciena-6500-types:INT;
          description
            "Compensation optimization scanning step size , ps/nm";
        }
        leaf s-dwell {
          yang:get-supported "true";
          type ciena-6500-types:INT;
          description
            "Scanning dwell time, second";
        }
        leaf tx-freq-prov {
          yang:get-supported "true";
          type ciena-6500-types:STRING;
          description
            "Provisioned TX Frequency in THz (xxx.xxxx)";
        }
        leaf tx-freq-min {
          default "0.00";
          yang:get-supported "true";
          type ciena-6500-types:STRING;
          description
            "Minimum TX Frequency value in THz (xxx.xxxx)";
        }
        leaf tx-freq-max {
          default "0.00";
          yang:get-supported "true";
          type ciena-6500-types:STRING;
          description
            "Maximum TX Frequency value in THz (xxx.xxxx)";
        }
        leaf enm-prov {
          yang:get-supported "true";
          type enumeration {
            enum MODE1 {
              description
                "ENM (Enhanced Non-linear Mitigation) mode 1";
            }
            enum MODE2 {
              description
                "ENM (Enhanced Non-linear Mitigation) mode 2";
            }
            enum AUTO {
              description
                "ENM (Enhanced Non-linear Mitigation) auto";
            }
          }
          description
            "Provisioned Enhanced Non-linear Mitigation mode";
        }
        leaf rx-enm {
          yang:get-supported "true";
          type enumeration {
            enum MODE1 {
              description
                "ENM (Enhanced Non-linear Mitigation) mode 1";
            }
            enum MODE2 {
              description
                "ENM (Enhanced Non-linear Mitigation) mode 2";
            }
            enum UNKNOWN {
              description
                "ENM (Enhanced Non-linear Mitigation) default";
            }
          }
          description
            "Enhanced Non-linear Mitigation mode";
        }
        leaf tx-enm {
          yang:get-supported "true";
          type enumeration {
            enum MODE1 {
              description
                "ENM (Enhanced Non-linear Mitigation) mode 1";
            }
            enum MODE2 {
              description
                "ENM (Enhanced Non-linear Mitigation) mode 2";
            }
            enum UNKNOWN {
              description
                "ENM (Enhanced Non-linear Mitigation) default";
            }
          }
          description
            "Enhanced Non-linear Mitigation mode";
        }
        leaf carrier-centering-mode {
          yang:get-supported "true";
          type ciena-6500-enums:ochCarrierCenteringMode;
          description
            "Laser centering mode";
        }
        leaf ccda {
          yang:get-supported "true";
          type ciena-6500-enums:ccda;
          description
            "TX Channel Contention Detection and Avoidance";
        }
        leaf txb {
          yang:get-supported "true";
          type ciena-6500-enums:txb;
          description
            "TX Power in Reduced State";
        }
        leaf secure-oh {
          yang:get-supported "true";
          type ciena-6500-enums:SecureOH;
          description
            "Secure Overhead Bytes";
        }
        leaf spli-mgmt {
          yang:get-supported "true";
          type ciena-6500-enums:spliMgmt;
          description
            "Identify if Port is Manageable by SPLI";
        }
        leaf encr-tcm {
          default "1";
          yang:get-supported "true";
          type ciena-6500-types:INT {
            range "1..6";
          }
          description
            "Active TCM Level for Encryption";
        }
        leaf encr-odu1 {
          yang:get-supported "true";
          type ciena-6500-types:INT;
          description
            "ODU Reserve Byte 1 for Encryption";
        }
        leaf encr-odu2 {
          yang:get-supported "true";
          type ciena-6500-types:INT;
          description
            "ODU Reserve Byte 2 for Encryption";
        }
        leaf spli-managed {
          yang:get-supported "true";
          type ciena-6500-enums:spliManaged;
          description
            "Identify if Port is Currently Managed by SPLI";
        }
        leaf role {
          yang:get-supported "true";
          type enumeration {
            enum PRIME {
              description
                "Prime of the group.";
            }
            enum MEMBER2 {
              description
                "Member of the group.";
            }
          }
          description
            "Indicates whether this OTM facility is the prime or member in a FLEX4 2X8QAM300G CP group";
        }
        leaf p-aid {
          yang:get-supported "true";
          type ciena-6500-types:IDENT;
          description
            "FLEX4 OCLD 2X8QAM300G CP group prime line port AID";
        }
        leaf m-aid {
          yang:get-supported "true";
          type ciena-6500-types:IDENT;
          description
            "FLEX4 OCLD 2X8QAM300G CP group member line port AID";
        }
        leaf odu-rate {
          yang:get-supported "true";
          type enumeration {
            enum ODUC2 {
              description
                "ODU layer rate is 2xODU4";
            }
            enum ODUC4 {
              description
                "ODU layer rate is 4xODU4";
            }
          }
          description
            " Number of ODU4s contained by the ODUCn layer in a 8QAM CP group";
        }
        leaf rx-pwr-l-thr {
          default "0";
          yang:get-supported "true";
          type ciena-6500-types:STRING;
          description
            "Provisioned Rx Power OOR low threshold";
        }
        leaf rx-pwr-h-thr {
          default "0";
          yang:get-supported "true";
          type ciena-6500-types:STRING;
          description
            "Provisioned Rx Power OOR high threshold";
        }
        leaf rx-ch-pwr-l-thr {
          default "0";
          yang:get-supported "true";
          type ciena-6500-types:STRING;
          description
            "Provisioned Rx channel Power OOR low threshold";
        }
        leaf rx-ch-pwr-h-thr {
          default "0";
          yang:get-supported "true";
          type ciena-6500-types:STRING;
          description
            "Provisioned Rx channel Power OOR high threshold";
        }
        leaf rx-pwr-thr-prov {
          yang:get-supported "true";
          type enumeration {
            enum ON {
              description
                "Use of provisioned thresholds is on";
            }
            enum OFF {
              description
                "Use of provisioned thresholds is off";
            }
          }
          description
            "Enable to use provisioned thresholds";
        }
        leaf prtl-srv {
          yang:get-supported "true";
          type enumeration {
            enum ON {
              description
                "Partial survivability is supported";
            }
            enum OFF {
              description
                "Partial survivability is not supported";
            }
          }
          description
            "Indicates partial survivability support";
        }
        leaf ttops {
          yang:get-supported "true";
          type ciena-6500-enums:BOOL_YES_NO;
          description
            "Transponder Triggered Switching Mode Enabled";
        }
        leaf ochtxsigbw3db {
          yang:get-supported "true";
          type ciena-6500-types:STRING;
          description
            "Supported 3dB bandwidth value";
        }
        leaf ochtxsigbw10db {
          yang:get-supported "true";
          type ciena-6500-types:STRING;
          description
            "Supported 10dB bandwidth value";
        }
        leaf ochtxminspecwth {
          yang:get-supported "true";
          type ciena-6500-types:STRING;
          description
            "Minimum spectral width";
        }
        leaf ochtxfreqres {
          yang:get-supported "true";
          type ciena-6500-types:STRING;
          description
            "Supported frequency resolution";
        }
        leaf laser-centering-range {
          yang:get-supported "true";
          type ciena-6500-types:STRING;
          description
            "Sets laser centering range";
        }
        leaf laser-freq-thr {
          yang:get-supported "true";
          type decimal64 {
            range "0.0..3.0";
            fraction-digits 1;
          }
          description
            "Laser Frequency Threshold";
        }
        leaf exp-res-time-prov {
          default "10";
          yang:get-supported "true";
          type ciena-6500-types:INT {
            range "0..255";
          }
          description
            "Provisioned Acquisition Holdoff Time";
        }
        leaf optical-sf-rept {
          yang:get-supported "true";
          type enumeration {
            enum ON {
              description
                "Optical signal failed will be reported.";
            }
            enum OFF {
              description
                "Optical signal failed will not be reported.";
            }
          }
          description
            "Indicates whether or not the optical signal failed standing condition will be reported.";
        }
        leaf mate-info {
          yang:get-supported "true";
          type string {
            length "0..64";
          }
          description
            "Slot and Port info of Mating Peer";
        }
        leaf pst {
          yang:get-supported "true";
          type ciena-6500-enums:PSTfac_RTRV;
          description
            "Identify the primary State";
        }
        leaf-list sst {
          yang:get-supported "true";
          type enumeration {
            enum AINS {
              description
                "Auto-In-Service";
            }
            enum MT {
              description
                "Maintenance";
            }
            enum FLT {
              description
                "Fault detected";
            }
            enum SGEO {
              description
                "Supporting Entity Outage (based on PSTQ of OOS-AU, OOS-AUMA only)";
            }
            enum LPBK {
              description
                "Loopback";
            }
            enum DISCD {
              description
                "Disconnected. (no transparent traffic connection on this facility)";
            }
            enum TSGEN {
              description
                "Test set generation";
            }
            enum TSMON {
              description
                "Test set monitor";
            }
            enum WRKRX {
              description
                "Active OTM Facility in Receiving Direction (in protection configuration only)";
            }
            enum WRKTX {
              description
                "Active OTM Facility in Transmitting Direction (in protection configuration only)";
            }
            enum STBYH {
              description
                "Hot Standby (in protection configuration only)";
            }
            enum PSI {
              description
                "Protection Switch Inhibited (in protection configuration only)";
            }
          }
          description
            "Secondary State";
        }
      }
    }
  }

  rpc port-disable-otm {
    description
      "Remove an OTM Facility";
    yang:handler "tl1";
    input {
      leaf otmaid {
        mandatory true;
        description
          "AID in format OTM1-shelf-slot-port, OTM4-shelf-slot-port, OTMC2-shelf-slot-port, OTM-shelf-slot-port";
        type ciena-6500-types:aid;
      }
      leaf sst {
        type ciena-6500-enums:RMVSSTMT;
        description
          "Identify Maintenance State";
      }
    }
  }

  rpc port-enable-otm {
    description
      "Restore an OTM Facility";
    yang:handler "tl1";
    input {
      leaf otmaid {
        mandatory true;
        description
          "AID in format OTM1-shelf-slot-port, OTM4-shelf-slot-port, OTMC2-shelf-slot-port, OTM-shelf-slot-port";
        type ciena-6500-types:aid;
      }
    }
  }

  rpc port-init-dispscan-otm {
    description
      "Dispersion scanning against OTM facility";
    yang:handler "tl1";
    input {
      leaf otmaid {
        mandatory true;
        description
          "AID in format OTM1-shelf-slot-port, OTM4-shelf-slot-port, OTMC2-shelf-slot-port, OTM-shelf-slot-port";
        type ciena-6500-types:aid;
      }
      leaf scan {
        type enumeration {
          enum START {
            description
              "Triggers Q-based Pre-dispersion compensation Scanning";
          }
          enum STOP {
            description
              "Cancels Q-based Pre-dispersion compensation Scanning";
          }
        }
        mandatory true;
        description
          "Q-based Pre-dispersion compensation Scanning";
      }
      leaf s-from {
        type ciena-6500-types:INT;
        description
          "FROM point of scanning range, ps/nm";
      }
      leaf s-to {
        type ciena-6500-types:INT;
        description
          "TO point of scanning range, ps/nm";
      }
      leaf s-step {
        type ciena-6500-types:INT;
        description
          "Compensation optimization scanning step size , ps/nm";
      }
      leaf s-dwell {
        type ciena-6500-types:INT;
        description
          "Scanning dwell time, second";
      }
    }
  }

  rpc port-show-sts192c {
    description
      "Retrieve Payload Facility: view the signal label parameters of an STS192C facility.";
    yang:handler "tl1";
    input {
      leaf sts192c {
        mandatory true;
        description
          "AID in format STS192C-shelf-slot-port-sts";
        type ciena-6500-types:aid;
      }
      leaf incsglbl {
        yang:get-supported "true";
        type enumeration {
          enum Y {
            description
              "Display Incoming Signal Label";
          }
          enum N {
            description
              "Exclude Incoming Signal Label";
          }
        }
        description
          "Omit querying the INCSGLBL value to improve retrieve time";
      }
    }
    output {
      list output {
        leaf sts192c {
          yang:get-supported "true";
          type ciena-6500-types:IDENT;
          description
            "aid";
        }
        leaf term {
          yang:get-supported "true";
          type enumeration {
            enum Y {
              description
                "Y=Terminated";
            }
            enum N {
              description
                "N=Not terminated";
            }
          }
          description
            "Y=Terminated/N=Not terminated";
        }
        leaf expsglbl {
          yang:get-supported "true";
          type ciena-6500-types:INT;
          description
            "Expected incoming signal label (C2) value";
        }
        leaf incsglbl {
          yang:get-supported "true";
          type enumeration {
            enum Y {
              description
                "Display Incoming Signal Label";
            }
            enum N {
              description
                "Exclude Incoming Signal Label";
            }
          }
          description
            "Omit querying the INCSGLBL value to improve retrieve time";
        }
        leaf sglbl {
          yang:get-supported "true";
          type ciena-6500-types:INT;
          description
            "Outgoing signal label (C2) value";
        }
        leaf trcformat {
          yang:get-supported "true";
          type enumeration {
            enum 16BYTE;
            enum 64BYTE;
          }
          description
            "Path trace format.";
        }
        leaf prime {
          yang:get-supported "true";
          type enumeration {
            enum OSS {
              description
                "Operation Support System Owned";
            }
            enum CPS {
              description
                "Control Plane System Owned";
            }
          }
          description
            "The owner of the payload facility";
        }
      }
    }
  }

  rpc port-show-tti-odu {
    description
      "Retrieve Trail Trace Identifier";
    yang:handler "tl1";
    input {
      leaf odun {
        mandatory true;
        description
          "AID in format ODU0-shelf-slot-port-payloadindex, ODU1-shelf-slot-port-payloadindex, ODUFLEX-shelf-slot-port-payloadindex, ODU4-shelf-slot-port-index";
        type ciena-6500-types:aid;
      }
      leaf msg-type {
        yang:get-supported "true";
        type ciena-6500-enums:ODUTTI;
        description
          "Message type to display";
      }
    }
    output {
      list output {
        leaf odun {
          yang:get-supported "true";
          type ciena-6500-types:IDENT;
          description
            "aid";
        }
        leaf tti-message {
          yang:get-supported "true";
          type ciena-6500-types:STRING;
          description
            "Trail Trace Identifier message";
        }
      }
    }
  }

  rpc port-show-ptp {
    description
      "Retrieve the PTP facility parameters";
    yang:handler "tl1";
    input {
      leaf ptp {
        mandatory true;
        description
          "AID in format PTP-shelf-slot-port, PTP-shelf-slot-portSsubport, PTP-shelf-slot-portPsubport, PTP-shelf-slotSsubslot-portSsubport, PTP-shelf-slot-ALL, PTP-shelf-slotSsubslot-port, PTP-shelf-ALL, ALL";
        type ciena-6500-types:aid;
      }
      leaf stats-info {
        yang:get-supported "true";
        type ciena-6500-enums:StatsInfoDefYes;
        description
          "Specify if Dynamic Status Information is to be included in the response.";
      }
      leaf disp-scan-info {
        yang:get-supported "true";
        type ciena-6500-enums:DispScanInfo;
        description
          "Indicates whether to include SFROM, STO, SSTEP, SDWELL, SCAN, OCHASSOCQ, OCHTXDISPFOUND in the response";
      }
      leaf stat-data {
        yang:get-supported "true";
        type ciena-6500-enums:StatData;
        description
          "This is represented data of STATDATA ";
      }
    }
    output {
      list output {
        leaf ptp {
          yang:get-supported "true";
          type ciena-6500-types:IDENT;
          description
            "aid";
        }
        leaf service-type {
          yang:get-supported "true";
          type ciena-6500-enums:ptpServiceType;
          description
            "Configured Service Type";
        }
        leaf role {
          yang:get-supported "true";
          type ciena-6500-enums:PtpRole;
          description
            "Role type in OTUCn-M configuration";
        }
        leaf bit-rate {
          yang:get-supported "true";
          type ciena-6500-enums:PtpRate;
          description
            "PTP Bit Rate";
        }
        leaf mod {
          yang:get-supported "true";
          type ciena-6500-enums:PtpMod;
          description
            "Modulation scheme";
        }
        leaf baud {
          yang:get-supported "true";
          type ciena-6500-enums:ptpBaud;
          description
            "OTSi Symbol rate";
        }
        leaf p-aid {
          yang:get-supported "true";
          type ciena-6500-types:aid;
          description
            "Specify the Prime PTP AID.";
        }
        leaf-list m-aid {
          yang:get-supported "true";
          type ciena-6500-types:aid;
          description
            "Specify the Member PTP AID List. Format: Member2&Member3&...";
        }
        leaf rx-fec-frmt {
          yang:get-supported "true";
          type enumeration {
            enum OFF {
              description
                "No FEC";
            }
            enum PFEC {
              description
                "Product FEC";
            }
            enum RS8 {
              description
                "Reed Solomon 8";
            }
            enum SCFEC {
              description
                "Super Concatenated FEC";
            }
            enum UFEC {
              description
                "UFEC";
            }
            enum QFEC {
              description
                "QFEC";
            }
            enum EFEC {
              description
                "EFEC";
            }
            enum LDPCFEC {
              description
                "LDPCFEC";
            }
            enum RS10_KP4 {
              description
                "RS10_KP4";
            }
            enum TFEC {
              description
                "TFEC";
            }
          }
          description
            "Type of Forward Error Correction on RX";
        }
        leaf tx-fec-frmt {
          yang:get-supported "true";
          type enumeration {
            enum OFF {
              description
                "No FEC";
            }
            enum PFEC {
              description
                "Product FEC";
            }
            enum RS8 {
              description
                "Reed Solomon 8";
            }
            enum SCFEC {
              description
                "Super ConcatenatedFEC";
            }
            enum UFEC {
              description
                "UFEC";
            }
            enum QFEC {
              description
                "QFEC";
            }
            enum EFEC {
              description
                "EFEC";
            }
            enum LDPCFEC {
              description
                "LDPCFEC";
            }
            enum RS10_KP4 {
              description
                "RS10_KP4";
            }
            enum TFEC {
              description
                "TFEC";
            }
          }
          description
            "Type of Forward Error Correction on TX";
        }
        leaf tx-path-id {
          yang:get-supported "true";
          type ciena-6500-types:INT {
            range "1..254";
          }
          description
            "TX path identifier";
        }
        leaf cond-type {
          yang:get-supported "true";
          type ciena-6500-enums:ptpCondType;
          description
            "The type of Tx conditioning to do in response to certain faults";
        }
        leaf tx-pwr {
          yang:get-supported "true";
          type ciena-6500-types:STRING;
          description
            "Provisioned TX Power in dBm (xx.x)";
        }
        leaf tx-wvlngth-prov {
          default "0.00";
          yang:get-supported "true";
          type ciena-6500-types:STRING;
          description
            "Provisioned Wavelength";
        }
        leaf differential-encoding {
          yang:get-supported "true";
          type enumeration {
            enum NONE {
              description
                "TR Control NONE";
            }
            enum HARD {
              description
                "TR Control HARD";
            }
            enum SOFT {
              description
                "TR Control SOFT";
            }
            enum XD {
              description
                "TR Control XD";
            }
          }
          description
            "OCH Differential Encoding";
        }
        leaf tx-spctrl-occp {
          yang:get-supported "true";
          type enumeration {
            enum NONE {
              description
                "NONE";
            }
            enum NARROW {
              description
                "NARROW";
            }
            enum WIDE20 {
              description
                "WIDE20";
            }
            enum WIDE25 {
              description
                "WIDE25";
            }
            enum WIDE30 {
              description
                "WIDE30";
            }
            enum WIDE40 {
              description
                "WIDE40";
            }
            enum WIDE50 {
              description
                "WIDE50";
            }
            enum MINSPACE20 {
              description
                "MINSPACE20";
            }
            enum MINSPACE25 {
              description
                "MINSPACE25";
            }
          }
          description
            "OCH Spectral Occupancy setting";
        }
        leaf label {
          yang:get-supported "true";
          type string {
            length "0..64";
          }
          description
            "User specified Label";
        }
        leaf-list rx-act-ln-pwr {
          yang:get-supported "true";
          type ciena-6500-types:STRING;
          description
            "Lane RX Power in dBm (xx.x) (Format: Lane1|Lane2|...)";
        }
        leaf-list tx-act-ln-pwr {
          yang:get-supported "true";
          type ciena-6500-types:STRING;
          description
            "Lane TX Power in dBm (xx.x) (Format: Lane1|Lane2|...)";
        }
        leaf och-tx-act-power {
          yang:get-supported "true";
          type ciena-6500-types:STRING;
          description
            "TX actual power in dBm (xx.x)";
        }
        leaf och-tx-min-power {
          yang:get-supported "true";
          type ciena-6500-types:STRING;
          description
            "TX minimum power in dBm (xx.x)";
        }
        leaf och-tx-max-power {
          yang:get-supported "true";
          type ciena-6500-types:STRING;
          description
            "TX maximum power in dBm (xx.x)";
        }
        leaf och-rx-act-power {
          yang:get-supported "true";
          type ciena-6500-types:STRING;
          description
            "RX actual power in dBm (xx.x)";
        }
        leaf och-rx-min-power {
          yang:get-supported "true";
          type ciena-6500-types:STRING;
          description
            "RX minimum power in dBm (xx.x)";
        }
        leaf och-rx-max-power {
          yang:get-supported "true";
          type ciena-6500-types:STRING;
          description
            "RX maximum power in dBm (xx.x)";
        }
        leaf och-tx-act-high-power {
          yang:get-supported "true";
          type ciena-6500-types:STRING;
          description
            "TX active high power in dBm (xx.x)";
        }
        leaf och-tx-act-low-power {
          yang:get-supported "true";
          type ciena-6500-types:STRING;
          description
            "TX active low power in dBm (xx.x)";
        }
        leaf och-rx-act-high-power {
          yang:get-supported "true";
          type ciena-6500-types:STRING;
          description
            "RX active high power in dBm (xx.x)";
        }
        leaf och-rx-act-low-power {
          yang:get-supported "true";
          type ciena-6500-types:STRING;
          description
            "RX active low power in dBm (xx.x)";
        }
        leaf tx-wvlngth-min {
          default "0.00";
          yang:get-supported "true";
          type ciena-6500-types:STRING;
          description
            "Minimum Wavelength Range";
        }
        leaf tx-wvlngth-max {
          default "0.00";
          yang:get-supported "true";
          type ciena-6500-types:STRING;
          description
            "Maximum Wavelength Range";
        }
        leaf tx-wvlngth-spacing {
          yang:get-supported "true";
          type ciena-6500-enums:ochTxWvlngthSpacing;
          description
            "OCH Wavelength Spacing, in nm";
        }
        leaf och-rx-ch-act-power {
          yang:get-supported "true";
          type ciena-6500-types:STRING;
          description
            "RX channel actual power in dBm (xx.x)";
        }
        leaf och-rx-ch-min-power {
          yang:get-supported "true";
          type ciena-6500-types:STRING;
          description
            "RX channel minimum power in dBm (xx.x)";
        }
        leaf och-rx-ch-max-power {
          yang:get-supported "true";
          type ciena-6500-types:STRING;
          description
            "RX channel maximum power in dBm (xx.x)";
        }
        leaf och-rx-echo-trace {
          yang:get-supported "true";
          type ciena-6500-types:STRING;
          description
            "TR Transmit Identifier Received";
        }
        leaf och-tx-trace {
          yang:get-supported "true";
          type ciena-6500-types:STRING;
          description
            "TR Transmit Identifier Received Expected";
        }
        leaf och-tx-assoc-far-end-rx {
          yang:get-supported "true";
          type ciena-6500-types:STRING;
          description
            "Transmitter associated far end receiver";
        }
        leaf och-max-pmd {
          yang:get-supported "true";
          type ciena-6500-types:STRING;
          description
            "Supported Mean DGD (Differential Group Delay) value";
        }
        leaf och-rx-act-pmd {
          yang:get-supported "true";
          type ciena-6500-types:STRING;
          description
            "Estimated Instance of DGD (Differential Group Delay) value";
        }
        leaf est-length {
          yang:get-supported "true";
          type ciena-6500-types:STRING;
          description
            "Estimated fiber length";
        }
        leaf laser-bias-end-of-life {
          yang:get-supported "true";
          type ciena-6500-types:STRING;
          description
            "Laser Bias Current.";
        }
        leaf rtd {
          yang:get-supported "true";
          type ciena-6500-types:STRING;
          description
            "OCH Round Trip Delay.";
        }
        leaf uni-latency {
          yang:get-supported "true";
          type ciena-6500-types:STRING;
          description
            "OCH Unidirectional Latency.";
        }
        leaf ains-time-left {
          yang:get-supported "true";
          type ciena-6500-types:TIME;
          description
            "The format will be \"HH-MM\" for the time left in AINS timeout.";
        }
        leaf line-type {
          yang:get-supported "true";
          type ciena-6500-enums:linetype;
          description
            "OCH Line Sys Type";
        }
        leaf pwr-bal-ctlr {
          yang:get-supported "true";
          type enumeration {
            enum DISABLED {
              description
                "Power Balance Controller Disabled";
            }
            enum ENABLED {
              description
                "Power Balance Controller Enabled";
            }
          }
          description
            "Provisioned Power Balance Controller Operating Mode";
        }
        leaf pwr-bal-offset {
          yang:get-supported "true";
          type ciena-6500-types:STRING;
          description
            "Provisioned Power Balance Offset in dB (xx.x)";
        }
        leaf pwr-bal-act-offset {
          yang:get-supported "true";
          type ciena-6500-types:STRING;
          description
            "Provisioned Power Balance Actual Offset in dB (xx.x)";
        }
        leaf tuning-mode {
          yang:get-supported "true";
          type ciena-6500-enums:ochTuningMode;
          description
            "Provisioned Tuning Mode";
        }
        leaf frr {
          yang:get-supported "true";
          type enumeration {
            enum DISABLED {
              description
                "DISABLED Mode";
            }
            enum ENABLED {
              description
                "ENABLED Mode";
            }
          }
          description
            "OCH Fast Receiver Recovery";
        }
        leaf frr-config {
          yang:get-supported "true";
          type enumeration {
            enum MATCHEDCD {
              description
                "Matched Chromatic Dispersion";
            }
            enum DIVERSECD2 {
              description
                "Diverse Chromatic Dispersion 2 Paths";
            }
          }
          description
            "OCH FRR Network Configuration";
        }
        leaf frr-path1-disp {
          default "AUTO";
          yang:get-supported "true";
          type ciena-6500-types:STRING;
          description
            "OCH FRR Link Dispersion for Path 1";
        }
        leaf frr-path2-disp {
          default "AUTO";
          yang:get-supported "true";
          type ciena-6500-types:STRING;
          description
            "OCH FRR Link Dispersion for Path 2";
        }
        leaf optimize-mode {
          yang:get-supported "true";
          type ciena-6500-enums:optimizeMode;
          description
            "Performance Optimization Mode";
        }
        leaf tx-mode {
          yang:get-supported "true";
          type ciena-6500-enums:TxMode;
          description
            "Transmitter Dispersion Mode";
        }
        leaf tx-disp-prov {
          yang:get-supported "true";
          type ciena-6500-types:STRING;
          description
            "Transmitter Dispersion Provisioned Value";
        }
        leaf path-disp-prov {
          yang:get-supported "true";
          type ciena-6500-types:STRING;
          description
            "Path Dispersion Value";
        }
        leaf och-tx-act-disp {
          yang:get-supported "true";
          type ciena-6500-types:STRING;
          description
            "Transmitter total actual link dispersion in the near-to-far direction";
        }
        leaf tx-disp-min {
          yang:get-supported "true";
          type ciena-6500-types:STRING;
          description
            "Minimum Transmitter Dispersion Value";
        }
        leaf tx-disp-max {
          yang:get-supported "true";
          type ciena-6500-types:STRING;
          description
            "Maximum Transmitter Dispersion Value";
        }
        leaf och-rx-act-disp {
          yang:get-supported "true";
          type ciena-6500-types:STRING;
          description
            "Receiver total actual link dispersion in the far-to-near direction";
        }
        leaf och-tx-pre-disp {
          yang:get-supported "true";
          type ciena-6500-types:STRING;
          description
            "Tx Precompensation Dispersion Value.";
        }
        leaf och-rx-post-disp {
          yang:get-supported "true";
          type ciena-6500-types:STRING;
          description
            "Rx Postcompensation Dispersion Value.";
        }
        leaf reach-spec {
          yang:get-supported "true";
          type ciena-6500-types:STRING;
          description
            "Reach Specification";
        }
        leaf tx-chrip {
          default "AUTO";
          yang:get-supported "true";
          type enumeration {
            enum AUTO {
              description
                "Automatic";
            }
            enum POSITIVE {
              description
                "Positive";
            }
            enum NEGATIVE {
              description
                "Negative";
            }
          }
          description
            "Positive or Negative Chirp setting";
        }
        leaf enm-prov {
          yang:get-supported "true";
          type ciena-6500-enums:ochenm;
          description
            "OCH ENM provisioning mode";
        }
        leaf ccda {
          yang:get-supported "true";
          type ciena-6500-enums:ccda;
          description
            "TX Channel Contention Detection and Avoidance";
        }
        leaf och-tx-blanking {
          yang:get-supported "true";
          type ciena-6500-enums:txb;
          description
            "Manually force the Line port TX power in reduced state.";
        }
        leaf tx-freq-prov {
          yang:get-supported "true";
          type ciena-6500-types:STRING;
          description
            "Provisioned TX Frequency in THz (xxx.xxxx)";
        }
        leaf tx-freq-min {
          default "0.00";
          yang:get-supported "true";
          type ciena-6500-types:STRING;
          description
            "Minimum TX Frequency value in THz (xxx.xxxx)";
        }
        leaf tx-freq-max {
          default "0.00";
          yang:get-supported "true";
          type ciena-6500-types:STRING;
          description
            "Maximum TX Frequency value in THz (xxx.xxxx)";
        }
        leaf carrier-centering-mode {
          yang:get-supported "true";
          type ciena-6500-enums:ochCarrierCenteringMode;
          description
            "Laser centering mode";
        }
        leaf rotation {
          yang:get-supported "true";
          type ciena-6500-enums:rotation;
          description
            "Jones Rotation Setting";
        }
        leaf tx-disp-found {
          yang:get-supported "true";
          type ciena-6500-types:STRING;
          description
            "Found the optimum Pre-dispersion compensation from the scanning, ps/nm";
        }
        leaf assoc-q {
          yang:get-supported "true";
          type ciena-6500-types:STRING;
          description
            "Q associated with the found optimum precomp";
        }
        leaf scan {
          yang:get-supported "true";
          type ciena-6500-enums:ScanState;
          description
            "Q-based Pre-dispersion compensation Scanning";
        }
        leaf s-from {
          yang:get-supported "true";
          type ciena-6500-types:STRING;
          description
            "FROM point of scanning range, ps/nm";
        }
        leaf s-to {
          yang:get-supported "true";
          type ciena-6500-types:STRING;
          description
            "TO point of scanning range, ps/nm";
        }
        leaf s-step {
          yang:get-supported "true";
          type ciena-6500-types:STRING;
          description
            "Compensation optimization scanning step size , ps/nm";
        }
        leaf s-dwell {
          yang:get-supported "true";
          type ciena-6500-types:STRING;
          description
            "Scanning dwell time, second";
        }
        leaf spli-mgmt {
          yang:get-supported "true";
          type ciena-6500-enums:spliMgmt;
          description
            "Identify if Port is Manageable by SPLI";
        }
        leaf spli-managed {
          yang:get-supported "true";
          type ciena-6500-enums:spliManaged;
          description
            "Identify if Port is Currently Managed by SPLI";
        }
        leaf rx-pwr-thr-prov {
          yang:get-supported "true";
          type enumeration {
            enum ON {
              description
                "Use of provisioned thresholds is on";
            }
            enum OFF {
              description
                "Use of provisioned thresholds is off";
            }
          }
          description
            "Enable to use provisioned thresholds";
        }
        leaf rx-pwr-l-thr {
          default "-22.5";
          yang:get-supported "true";
          type ciena-6500-types:STRING;
          description
            "Provisioned Rx Power OOR low threshold";
        }
        leaf rx-pwr-h-thr {
          default "5.5";
          yang:get-supported "true";
          type ciena-6500-types:STRING;
          description
            "Provisioned Rx Power OOR high threshold";
        }
        leaf rx-ch-pwr-l-thr {
          default "-18.5";
          yang:get-supported "true";
          type ciena-6500-types:STRING;
          description
            "Provisioned Rx channel Power OOR low threshold";
        }
        leaf rx-ch-pwr-h-thr {
          default "7";
          yang:get-supported "true";
          type ciena-6500-types:STRING;
          description
            "Provisioned Rx channel Power OOR high threshold";
        }
        leaf och-tx-sig-bw-3db {
          default "35.0";
          yang:get-supported "true";
          type ciena-6500-types:STRING;
          description
            "Supported 3dB bandwidth value";
        }
        leaf och-tx-sig-bw-10db {
          default "38.6";
          yang:get-supported "true";
          type ciena-6500-types:STRING;
          description
            "Supported 10dB bandwidth value";
        }
        leaf och-tx-min-spec-width {
          default "37.5";
          yang:get-supported "true";
          type ciena-6500-types:STRING;
          description
            "Minimum spectral width";
        }
        leaf och-tx-freqr-es {
          default "0.1";
          yang:get-supported "true";
          type ciena-6500-types:STRING;
          description
            "Supported frequency resolution";
        }
        leaf laser-centering-range {
          default "2.5";
          yang:get-supported "true";
          type ciena-6500-types:STRING;
          description
            "Provisioned laser centering range";
        }
        leaf ttops {
          yang:get-supported "true";
          type ciena-6500-enums:BOOL_YES_NO;
          description
            "Transponder Triggered Switching Mode Enabled";
        }
        leaf fec-frmt {
          yang:get-supported "true";
          type ciena-6500-enums:PTP_FECFrmt;
          description
            "Tx/Rx FEC Format";
        }
        leaf trans-mode {
          yang:get-supported "true";
          type ciena-6500-enums:ptpTransMode;
          description
            "Transmission Mode";
        }
        leaf act_trans-mode {
          yang:get-supported "true";
          type ciena-6500-enums:ptpTransMode;
          description
            "Actual Transmission Mode";
        }
        leaf pre-fec-sf-th-lev {
          default "0.00";
          yang:get-supported "true";
          type decimal64 {
            range "-1.00..1.00";
            fraction-digits 2;
          }
          description
            "Pre-FEC Signal Fail Threshold";
        }
        leaf pre-fec-sd-th-lev {
          default "0.50";
          yang:get-supported "true";
          type decimal64 {
            range "-1.00..3.50";
            fraction-digits 2;
          }
          description
            "Pre-FEC Signal Degrade Threshold";
        }
        leaf tx-pid {
          default "0";
          yang:get-supported "true";
          type ciena-6500-types:INT {
            range "0..7";
          }
          description
            "Tx Physical Layer ID";
        }
        leaf tx-gid {
          default "0";
          yang:get-supported "true";
          type ciena-6500-types:INT {
            range "0..31";
          }
          description
            "Tx Group ID";
        }
        leaf pre-fec-sf-th-ber {
          default "0.0";
          yang:get-supported "true";
          type ciena-6500-types:STRING;
          description
            "The corresponding BER for a given Pre-FEC SF Threshold setting in dDQ";
        }
        leaf pre-fec-sd-th-ber {
          default "0.0";
          yang:get-supported "true";
          type ciena-6500-types:STRING;
          description
            "The corresponding BER for a given Pre-FEC SD Threshold setting in dDQ";
        }
        leaf rx-pid {
          default "0";
          yang:get-supported "true";
          type union {
            type enumeration {
              enum UNKNOWN;
            }
            type ciena-6500-types:INT {
              range "0..7";
            }
          }
          description
            "Rx Physical Layer ID";
        }
        leaf rx-gid {
          default "0";
          yang:get-supported "true";
          type union {
            type enumeration {
              enum UNKNOWN;
            }
            type ciena-6500-types:INT {
              range "0..31";
            }
          }
          description
            "Rx Group ID";
        }
        leaf tx-phy-map {
          yang:get-supported "true";
          type ciena-6500-types:STRING;
          description
            "Tx Physical Mapping Bitmap";
        }
        leaf rx-phy-map {
          yang:get-supported "true";
          type ciena-6500-types:STRING;
          description
            "Rx Physical Mapping Bitmap";
        }
        leaf modem-class {
          yang:get-supported "true";
          type ciena-6500-enums:ptpModemClass;
          description
            "Modem Class";
        }
        leaf reach-class {
          yang:get-supported "true";
          type ciena-6500-enums:ptpReachClass;
          description
            "Reach Class";
        }
        leaf linkOpt-mode {
          yang:get-supported "true";
          type ciena-6500-enums:ptpLnkOptMode;
          description
            "Link Optimization Mode";
        }
        leaf reach-type {
          yang:get-supported "true";
          type ciena-6500-enums:ptpReachType;
          description
            "Reach Type";
        }
        leaf lnkCustom1 {
          yang:get-supported "true";
          type ciena-6500-enums:ptpLnkCustom1;
          description
            "Link Custom1";
        }
        leaf lnkCustom2 {
          yang:get-supported "true";
          type ciena-6500-enums:ptpLnkCustom2;
          description
            "Link Custom2";
        }
        leaf allocated-spec-width {
          yang:get-supported "true";
          type ciena-6500-types:STRING;
          description
            "Allocated Spectral Width";
        }
        leaf laser-off-mode {
          yang:get-supported "true";
          type ciena-6500-enums:ptpLaserOffMode;
          description
            "Laser Off Mode";
        }
        leaf laser-freq-thr {
          yang:get-supported "true";
          type decimal64 {
            range "0.0..3.0";
            fraction-digits 1;
          }
          description
            "Laser Frequency Threshold";
        }
        leaf line-build-out {
          default "0";
          yang:get-supported "true";
          type ciena-6500-types:INT {
            range "0..5";
          }
          description
            "Line Build Out";
        }
        leaf line-cde {
          yang:get-supported "true";
          type ciena-6500-enums:ptpLineCde;
          description
            "Line Coding";
        }
        leaf line-fail {
          yang:get-supported "true";
          type ciena-6500-enums:ptpLineFail;
          description
            "Line Fail";
        }
        leaf rx-mon {
          yang:get-supported "true";
          type enumeration {
            enum YES;
            enum NO;
          }
          description
            "Indicate if the signal is monitored in the Rx direction for alarms and PMs and OMs.";
        }
        leaf rx-term {
          yang:get-supported "true";
          type enumeration {
            enum YES;
            enum NO;
          }
          description
            "Indicate if the signal is terminated in the Rx direction or not.";
        }
        leaf rqst-trans-mode {
          yang:get-supported "true";
          type ciena-6500-enums:ptpTransMode;
          description
            "Requested Transmission Mode";
        }
        leaf saved-trans-mode {
          yang:get-supported "true";
          type ciena-6500-enums:ptpTransMode;
          description
            "Saved Actual Applied Transmission Mode";
        }
        leaf rqst-linkOpt-mode {
          yang:get-supported "true";
          type ciena-6500-enums:ptpLnkOptMode;
          description
            "Requested Link Optimization Mode";
        }
        leaf act-linkOpt-mode {
          yang:get-supported "true";
          type ciena-6500-enums:ptpLnkOptMode;
          description
            "Actual Applied Link Optimization Mode";
        }
        leaf saved-linkOpt-mode {
          yang:get-supported "true";
          type ciena-6500-enums:ptpLnkOptMode;
          description
            "Saved Actual Applied Link Optimization Mode";
        }
        leaf rqst-tx-wvlngth {
          yang:get-supported "true";
          type ciena-6500-types:STRING;
          description
            "Requested Wavelength";
        }
        leaf act-tx-wvlngth {
          yang:get-supported "true";
          type ciena-6500-types:STRING;
          description
            "Actual Applied Wavelength";
        }
        leaf rqst-tx-wvlngth-spacing {
          yang:get-supported "true";
          type ciena-6500-enums:ochTxWvlngthSpacing;
          description
            "Requested Wavelength Spacing, in nm";
        }
        leaf rqst-tx-freq {
          yang:get-supported "true";
          type ciena-6500-types:STRING;
          description
            "Requested TX Frequency in THz (xxx.xxxx)";
        }
        leaf act-tx-freq {
          yang:get-supported "true";
          type ciena-6500-types:STRING;
          description
            "Actual Applied TX Frequency in THz (xxx.xxxx)";
        }
        leaf rqst-tx-pwr {
          yang:get-supported "true";
          type ciena-6500-types:STRING;
          description
            "Requested TX Power in dBm (xx.x)";
        }
        leaf rqst-tx-mode {
          yang:get-supported "true";
          type ciena-6500-enums:TxMode;
          description
            "Requested Transmitter Dispersion Mode";
        }
        leaf act-tx-mode {
          yang:get-supported "true";
          type ciena-6500-enums:TxMode;
          description
            "Actual Applied Transmitter Dispersion Mode";
        }
        leaf rqst-tx-disp {
          yang:get-supported "true";
          type ciena-6500-types:STRING;
          description
            "Requested Transmitter Dispersion Value";
        }
        leaf act-tx-disp {
          yang:get-supported "true";
          type ciena-6500-types:STRING;
          description
            "Actual Applied Transmitter Dispersion Value";
        }
        leaf rqst-path-disp {
          yang:get-supported "true";
          type ciena-6500-types:STRING;
          description
            "Requested Path Dispersion Value";
        }
        leaf act-path-disp {
          yang:get-supported "true";
          type ciena-6500-types:STRING;
          description
            "Actual Applied Path Dispersion Value";
        }
        leaf rqst-carrier-centering-mode {
          yang:get-supported "true";
          type ciena-6500-enums:ochCarrierCenteringMode;
          description
            "Requested Laser centering mode";
        }
        leaf act-carrier-centering-mode {
          yang:get-supported "true";
          type ciena-6500-enums:ochCarrierCenteringMode;
          description
            "Actual Applied Laser centering mode";
        }
        leaf rqst-laser-centering-range {
          yang:get-supported "true";
          type ciena-6500-types:STRING;
          description
            "Requested laser centering range";
        }
        leaf act-laser-centering-range {
          yang:get-supported "true";
          type ciena-6500-types:STRING;
          description
            "Actual Applied laser centering range";
        }
        leaf rqst-ccda {
          yang:get-supported "true";
          type ciena-6500-enums:ccda;
          description
            "Requested Channel Contention Detection and Avoidance";
        }
        leaf act-ccda {
          yang:get-supported "true";
          type ciena-6500-enums:ccda;
          description
            "Actual Applied Channel Contention Detection and Avoidance";
        }
        leaf rqst-och-tx-blanking {
          yang:get-supported "true";
          type ciena-6500-enums:txb;
          description
            "Requested TX power in reduced state.";
        }
        leaf act-och-tx-blanking {
          yang:get-supported "true";
          type ciena-6500-enums:txb;
          description
            "Actual Applied TX power in reduced state.";
        }
        leaf rqst-line-type {
          yang:get-supported "true";
          type ciena-6500-enums:linetype;
          description
            "Requested Line Sys Type";
        }
        leaf rqst-allocated-spec-width {
          yang:get-supported "true";
          type ciena-6500-types:STRING;
          description
            "Requested Allocated Spectral Width";
        }
        leaf rqst-exp-res-time {
          yang:get-supported "true";
          type union {
            type enumeration {
              enum UNKNOWN;
            }
            type ciena-6500-types:INT {
              range "0..100";
            }
          }
          description
            "Requested Acquisition Holdoff Time";
        }
        leaf exp-res-time-prov {
          default "10";
          yang:get-supported "true";
          type ciena-6500-types:INT {
            range "0..100";
          }
          description
            "Provisioned Acquisition Holdoff Time";
        }
        leaf act-exp-res-time {
          yang:get-supported "true";
          type union {
            type enumeration {
              enum UNKNOWN;
            }
            type ciena-6500-types:INT {
              range "0..100";
            }
          }
          description
            "Actual Applied Acquisition Holdoff Time";
        }
        leaf rqst-tuning-mode {
          yang:get-supported "true";
          type ciena-6500-enums:ochTuningMode;
          description
            "Requested Tuning Mode";
        }
        leaf act-tuning-mode {
          yang:get-supported "true";
          type ciena-6500-enums:ochTuningMode;
          description
            "Activated Tuning Mode";
        }
        leaf ser-path-disp-min-prov {
          yang:get-supported "true";
          type ciena-6500-types:STRING;
          description
            "Provisioned Path Dispersion Minimum for the SEARCH mode";
        }
        leaf ser-path-disp-max-prov {
          yang:get-supported "true";
          type ciena-6500-types:STRING;
          description
            "Provisioned Path Dispersion Maximum for the SEARCH mode";
        }
        leaf mate-info {
          yang:get-supported "true";
          type string {
            length "0..64";
          }
          description
            "";
        }
        leaf laser-status {
          yang:get-supported "true";
          type ciena-6500-enums:laserStatus;
          description
            "Laser status";
        }
        leaf lqs-managed {
          yang:get-supported "true";
          type ciena-6500-enums:lqsManaged;
          description
            "Liquid Spectrum managed";
        }
        leaf rqst-lqs-managed {
          yang:get-supported "true";
          type ciena-6500-enums:lqsManaged;
          description
            "Requested Liquid Spectrum managed";
        }
        leaf laser-tuned {
          yang:get-supported "true";
          type ciena-6500-enums:lasertuned;
          description
            "Laser tuning status";
        }
        leaf hold-off {
          default "0";
          yang:get-supported "true";
          type ciena-6500-types:INT {
            range "0 | 10 | 20..1000";
          }
          description
            "HoldOff signal conditioning timer";
        }
        leaf ccda-thr {
          default "-14.0";
          yang:get-supported "true";
          type decimal64 {
            range "-30.0..5.0";
            fraction-digits 1;
          }
          description
            "Provisioned CCDA threshold";
        }
        leaf said {
          yang:get-supported "true";
          type ciena-6500-types:aid;
          description
            "Specify the Service ODUCTP AID for Mate to Mate Interconnection";
        }
        leaf optical-sf-rept {
          yang:get-supported "true";
          type ciena-6500-enums:opticalSfRept;
          description
            "Optical Signal Failed reporting status ";
        }
        leaf los-thr {
          default "-35.0";
          yang:get-supported "true";
          type decimal64 {
            range "-40.0..5.0";
            fraction-digits 1;
          }
          description
            "loss of signal threshold";
        }
        leaf pst {
          yang:get-supported "true";
          type ciena-6500-enums:PSTfac_RTRV;
          description
            "Identify the primary State";
        }
        leaf-list sst {
          yang:get-supported "true";
          type ciena-6500-enums:SSTfac;
          description
            "Secondary State";
        }
      }
    }
  }

  rpc port-disable-ptp {
    description
      "Switch PTP Facility Out of Service";
    yang:handler "tl1";
    input {
      leaf ptp {
        mandatory true;
        description
          "AID in format PTP-shelf-slot-port, PTP-shelf-slot-portSsubport, PTP-shelf-slot-portPsubport, PTP-shelf-slotSsubslot-portSsubport, PTP-shelf-slotSsubslot-port";
        type ciena-6500-types:aid;
      }
      leaf sst {
        type ciena-6500-enums:RMVSSTMT;
        description
          "Remove facility from Maintenance State";
      }
    }
  }

  rpc port-enable-ptp {
    description
      "Switch PTP Facility In Service";
    yang:handler "tl1";
    input {
      leaf ptp {
        mandatory true;
        description
          "AID in format PTP-shelf-slot-port, PTP-shelf-slot-portSsubport, PTP-shelf-slot-portPsubport, PTP-shelf-slotSsubslot-port";
        type ciena-6500-types:aid;
      }
    }
  }

  rpc port-init-dispscan-ptp {
    description
      "Dispersion scanning against PTP facility";
    yang:handler "tl1";
    input {
      leaf ptp {
        mandatory true;
        description
          "AID in format PTP-shelf-slot-port, PTP-shelf-slot-portSsubport, PTP-shelf-slot-portPsubport";
        type ciena-6500-types:aid;
      }
      leaf scan {
        type ciena-6500-enums:ScanState;
        mandatory true;
        description
          "Q-based Pre-dispersion compensation Scanning";
      }
      leaf s-from {
        type ciena-6500-types:STRING;
        description
          "FROM point of scanning range, ps/nm";
      }
      leaf s-to {
        type ciena-6500-types:STRING;
        description
          "TO point of scanning range, ps/nm";
      }
      leaf s-step {
        type ciena-6500-types:STRING;
        description
          "Compensation optimization scanning step size , ps/nm";
      }
      leaf s-dwell {
        type ciena-6500-types:STRING;
        description
          "Scanning dwell time, second";
      }
    }
  }

  rpc port-show-otuttp {
    description
      "Retrieve the OTUTTP facility parameters";
    yang:handler "tl1";
    input {
      leaf otu {
        mandatory true;
        description
          "AID in format OTUTTP-shelf-slot-port, OTUTTP-shelf-slot-portSsubport, OTUTTP-shelf-slotSsubslot-portSsubport, OTUTTP-shelf-slot-ALL, OTUTTP-shelf-ALL, ALL, OTUTTP-shelf-slot-portPsubport, OTUTTP-shelf-slotSsubslot-port";
        type ciena-6500-types:aid;
      }
      leaf stats-info {
        yang:get-supported "true";
        type ciena-6500-enums:StatsInfoDefYes;
        description
          "Specify if Dynamic Status Information is to be included in the response.";
      }
    }
    output {
      list output {
        leaf otu {
          yang:get-supported "true";
          type ciena-6500-types:IDENT;
          description
            "aid";
        }
        leaf rate {
          yang:get-supported "true";
          type ciena-6500-enums:OtuRate;
          description
            "OTUCn Rate";
        }
        leaf label {
          yang:get-supported "true";
          type string {
            length "0..64";
          }
          description
            "User specified Label";
        }
        leaf rout-sig-disabled {
          yang:get-supported "true";
          type enumeration {
            enum NO {
              description
                "Routing signalling enabled";
            }
            enum YES {
              description
                "Routing signalling disabled";
            }
          }
          description
            "Specifies whether Routing Signalling is disabled on this TTP. When to NO, the OSRP will have control over the ODUs created under this TTP and no user created ODU will be allowed.";
        }
        leaf otu-sd-th-lev {
          yang:get-supported "true";
          type ciena-6500-types:INT;
          description
            "OTU Signal Degrade Threshold Level";
        }
        leaf otu-sf-th-lev {
          yang:get-supported "true";
          type ciena-6500-types:INT;
          description
            "OTU Signal Fail Threshold Level";
        }
        leaf rx-fec-frmt {
          yang:get-supported "true";
          type ciena-6500-enums:OTU_FECFrmt;
          description
            "Type of Forward Error Correction on RX";
        }
        leaf tx-fec-frmt {
          yang:get-supported "true";
          type ciena-6500-enums:OTU_FECFrmt;
          description
            "Type of Forward Error Correction on TX";
        }
        leaf oper-chg-evt {
          yang:get-supported "true";
          type enumeration {
            enum ON {
              description
                "Enable OTU Operator Specific TTI Change event";
            }
            enum OFF {
              description
                "Disable OTU Operator Specific TTI Change event";
            }
          }
          description
            "To enable or disable OTU Operator Specific TTI Change events";
        }
        leaf sapi-chg-evt {
          yang:get-supported "true";
          type enumeration {
            enum ON {
              description
                "Enable OTU SAPI Specific TTI Change event";
            }
            enum OFF {
              description
                "Disable OTU SAPI Specific TTI Change event";
            }
          }
          description
            "To enable or disable OTU SAPI Specific TTI Change events";
        }
        leaf dapi-chg-evt {
          yang:get-supported "true";
          type enumeration {
            enum ON {
              description
                "Enable OTU DAPI Specific TTI Change event";
            }
            enum OFF {
              description
                "Disable OTU DAPI Specific TTI Change event";
            }
          }
          description
            "To enable or disable OTU DAPI Specific TTI Change events";
        }
        leaf tx-sapi {
          yang:get-supported "true";
          type string {
            length "0..15";
          }
          description
            "The Source Access Point Identifier (SAPI), provisioned by the managing system at the termination source, to be placed in the Trail Trace Identifier (TTI) overhead position of the source of a trail.";
        }
        leaf tx-dapi {
          yang:get-supported "true";
          type string {
            length "0..15";
          }
          description
            "The Destination Access Point Identifier (DAPI), provisioned by the managing system at the termination source, to be placed in the Trail Trace Identifier (TTI) overhead position of the source of a trail.";
        }
        leaf tx-oper {
          yang:get-supported "true";
          type string {
            length "0..32";
          }
          description
            "The operator specific part of the Trail Trace Identifier (TTI) information, provisioned by the managing system at the termination source, to be placed in the TTI overhead position of the source of a trail.";
        }
        leaf ex-sapi {
          yang:get-supported "true";
          type string {
            length "0..15";
          }
          description
            "The expected Source Access Point Identifier (SAPI), provisioned by the managing system, to be compared with the received SAPI at the overhead position of the sink for the purpose of checking the integrity of connectivity. ";
        }
        leaf ex-dapi {
          yang:get-supported "true";
          type string {
            length "0..15";
          }
          description
            "The expected Destination Access Point Identifier (DAPI), provisioned by the managing system, to be compared with the received DAPI at the overhead position of the sink for the purpose of checking the integrity of connectivity. ";
        }
        leaf ex-oper {
          yang:get-supported "true";
          type string {
            length "0..32";
          }
          description
            "The expected operator specific part of the Trail Trace Identifier (TTI) information, provisioned by the managing system at the termination source, to be placed in the TTI overhead position of the source of a trail.";
        }
        leaf rx-sapi {
          yang:get-supported "true";
          type string {
            length "0..15";
          }
          description
            "The Source Access Point Identifier (SAPI) recovered from the Trail Trace Identifier (TTI) overhead position at the sink of a trail.";
        }
        leaf rx-dapi {
          yang:get-supported "true";
          type string {
            length "0..15";
          }
          description
            "The Destination Access Point Identifier (DAPI) recovered from the Trail Trace Identifier (TTI) overhead position at the sink of a trail.";
        }
        leaf rx-oper {
          yang:get-supported "true";
          type string {
            length "0..32";
          }
          description
            "The operator specific part of the Trail Trace Identifier (TTI) information, recovered from the TTI overhead position at the sink of a trail.";
        }
        leaf tf-mode {
          yang:get-supported "true";
          type ciena-6500-enums:otntfMode;
          description
            "Trace Fail Mode";
        }
        leaf tim-enable {
          yang:get-supported "true";
          type ciena-6500-enums:TIMEN;
          description
            "The Trail Trace Identifier Mismatch (TIM) controls checking for Trace Identifier Mismatch fault detection. ";
        }
        leaf osrp-tcm-level {
          yang:get-supported "true";
          type ciena-6500-types:INT {
            range "1..6";
          }
          description
            "This attribute specifies the TCM level for the OSRP created ODUs under this OTUTTP. The value of 0 indicates that no TCM will be created. The default value is specified by the attribute OSRPTCMLEVEL in the command ED-SYS.";
        }
        leaf num-ts {
          default "1";
          yang:get-supported "true";
          type ciena-6500-types:INT {
            range "1..320";
          }
          description
            "Used to identify the number of tributaries comprising this TTP. For on OTN TTP, this can change based on potential configuration of desired payload type (e.g. for ODU1 with OPVC payload, this value is 16; with CBR it is 1).";
        }
        leaf osrp-channel {
          yang:get-supported "true";
          type enumeration {
            enum NONE;
            enum GCC0;
            enum GCC1;
            enum GCC2;
          }
          description
            "The OSRP channel";
        }
        leaf pre-fec-sf-th-lev {
          yang:get-supported "true";
          type ciena-6500-types:STRING;
          description
            "Pre-FEC Signal Fail Threshold Level. Parameter applies when FEC is ON";
        }
        leaf pre-fec-sf-th-ber {
          yang:get-supported "true";
          type ciena-6500-types:STRING;
          description
            "Pre-FEC Signal Fail Threshold Bit Error Rate. Parameter applies when FEC is ON";
        }
        leaf pre-fec-sd-th-lev {
          yang:get-supported "true";
          type ciena-6500-types:STRING;
          description
            "Pre-FEC Signal Degrade Threshold Level. Parameter applies when FEC is ON";
        }
        leaf pre-fec-sd-th-ber {
          yang:get-supported "true";
          type ciena-6500-types:STRING;
          description
            "Pre-FEC Signal Degrade Threshold Bit Error Rate. Parameter applies when FEC is ON";
        }
        leaf supported-term-pt {
          yang:get-supported "true";
          type ciena-6500-types:aid;
          description
            "The supporting Termination Point.";
        }
        leaf local-sup-cacline-id {
          yang:get-supported "true";
          type ciena-6500-types:STRING;
          description
            "The generic cacline end point representing this facility shown in 54xx nomenclature (<bay>-<A|C>-<slot>-<port>)";
        }
        leaf timing-reference {
          yang:get-supported "true";
          type enumeration {
            enum N {
              description
                "Not a timing reference";
            }
            enum Y {
              description
                "Is a timing reference";
            }
          }
          description
            "Indicates whether the facility is being used as a timing reference";
        }
        leaf secure-oh {
          yang:get-supported "true";
          type ciena-6500-enums:SecureOH;
          description
            "Secure Overhead Bytes";
        }
        leaf otu-oh-non-term {
          yang:get-supported "true";
          type enumeration {
            enum NONE {
              description
                "Entire GCC OH terminated";
            }
            enum GCC0 {
              description
                "GCC0 portion of OTU OH not terminated";
            }
            enum GCC0MODE1 {
              description
                "GCC0MODE1 portion of OTU OH not terminated";
            }
          }
          description
            "Indicating whether to termiate GCC OH or not";
        }
        leaf encryption-tcm {
          default "1";
          yang:get-supported "true";
          type ciena-6500-types:INT {
            range "1..6";
          }
          description
            "This attribute specifies the TCM level for encryption.";
        }
        leaf encr-odu1 {
          yang:get-supported "true";
          type ciena-6500-enums:EncrByte;
          description
            "Encryption Byte1";
        }
        leaf hold-off {
          default "0";
          yang:get-supported "true";
          type ciena-6500-types:INT {
            range "0 | 10 | 20..1000";
          }
          description
            "HoldOff signal conditioning timer";
        }
        leaf hold-on {
          default "0";
          yang:get-supported "true";
          type ciena-6500-types:INT {
            range "0 | 2 | 4..500";
          }
          description
            "HoldOn signal conditioning timer";
        }
        leaf ains-time-left {
          yang:get-supported "true";
          type ciena-6500-types:TIME;
          description
            "The format will be HH-MM for the time left in AINS timeout.";
        }
        leaf otu-act-rate {
          yang:get-supported "true";
          type ciena-6500-enums:OtuActRate;
          description
            "Actual OTUCn rate, OTUCn(n=1..8)";
        }
        leaf act-num-ts {
          default "20";
          yang:get-supported "true";
          type ciena-6500-types:INT {
            range "20..320";
          }
          description
            "";
        }
        leaf rx-mon {
          yang:get-supported "true";
          type ciena-6500-enums:BOOL_YES_NO_defaultYES;
          description
            "Indicate if the signal is monitored in the Rx direction for alarms and PMs and OMs.";
        }
        leaf rx-term {
          yang:get-supported "true";
          type ciena-6500-enums:BOOL_YES_NO_defaultYES;
          description
            "Indicate if the signal is terminated in the Rx direction or not.";
        }
        leaf tx-mon {
          yang:get-supported "true";
          type ciena-6500-enums:BOOL_YES_NO_defaultNO;
          description
            "Indicate if the signal is monitored in the Tx direction for alarms and PMs and OMs.";
        }
        leaf tx-term {
          yang:get-supported "true";
          type ciena-6500-enums:BOOL_YES_NO_defaultNO;
          description
            "Indicate if the signal is terminated in the Tx direction for alarms and PMs and OMs.";
        }
        leaf degm-intv {
          yang:get-supported "true";
          type ciena-6500-types:INT {
            range "2..10";
          }
          description
            "Consecutive bad intervals required to declare signal degrade";
        }
        leaf degthr-percentage {
          yang:get-supported "true";
          type ciena-6500-types:INT {
            range "1..1000";
          }
          description
            "Percentage of errored blocks required to declare an interval bad";
        }
        leaf ts-profile {
          yang:get-supported "true";
          type ciena-6500-enums:otuTSProfile;
          description
            "TS Profile";
        }
        leaf osrp-line-mode {
          yang:get-supported "true";
          type enumeration {
            enum ENTIREPORT {
              description
                "This means an OSRP line is at the OTUCn rate.The value disables the OSRP embedded lines feature ";
            }
            enum NXODU4 {
              description
                "This value enables the OSRP embedded lines feature ";
            }
          }
          description
            "This parameter controls the embedded lines behaviour. User can enable/disable the embedded lines using this parameter(Param is applicable only on T-Series shelf.)";
        }
        leaf pst {
          yang:get-supported "true";
          type ciena-6500-enums:PSTfac_RTRV;
          description
            "Identify the primary State";
        }
        leaf-list sst {
          yang:get-supported "true";
          type ciena-6500-enums:SSTfac;
          description
            "Secondary State";
        }
      }
    }
  }

  rpc port-disable-otuttp {
    description
      "Switch OTUTTP Facility Out of Service";
    yang:handler "tl1";
    input {
      leaf otu {
        mandatory true;
        description
          "AID in format OTUTTP-shelf-slot-port, OTUTTP-shelf-slot-portSsubport, OTUTTP-shelf-slot-portPsubport, OTUTTP-shelf-slotSsubslot-port";
        type ciena-6500-types:aid;
      }
      leaf sst {
        type ciena-6500-enums:RMVSSTMT;
        description
          "Remove facility from Maintenance State";
      }
    }
  }

  rpc port-enable-otuttp {
    description
      "Switch OTUTTP Facility In Service";
    yang:handler "tl1";
    input {
      leaf otu {
        mandatory true;
        description
          "AID in format OTUTTP-shelf-slot-port, OTUTTP-shelf-slot-portSsubport, OTUTTP-shelf-slot-portPsubport, OTUTTP-shelf-slotSsubslot-port";
        type ciena-6500-types:aid;
      }
    }
  }

  rpc port-operate-loopback-otuttp {
    description
      "Operate loopback on specified facility.";
    yang:handler "tl1";
    input {
      leaf otu {
        mandatory true;
        description
          "AID in format OTUTTP-shelf-slot-port, OTUTTP-shelf-slot-portSsubport, OTUTTP-shelf-slot-portPsubport";
        type ciena-6500-types:aid;
      }
      leaf loopback-type {
        type enumeration {
          enum FACILITY {
            description
              "Signal looped toward the equipment";
          }
          enum TERMINAL {
            description
              "Signal looped away from the equipment";
          }
        }
        description
          "Loopback Type";
      }
    }
  }

  rpc port-release-loopback-otuttp {
    description
      "Release loopback on specified facility.";
    yang:handler "tl1";
    input {
      leaf otu {
        mandatory true;
        description
          "AID in format OTUTTP-shelf-slot-port, OTUTTP-shelf-slot-portSsubport, OTUTTP-shelf-slot-portPsubport";
        type ciena-6500-types:aid;
      }
    }
  }

  rpc port-show-loopback-otuttp {
    description
      "Retrieve loopback settings.";
    yang:handler "tl1";
    input {
      leaf otu {
        mandatory true;
        description
          "AID in format OTUTTP-shelf-slot-port, OTUTTP-shelf-slot-portSsubport, OTUTTP-shelf-slot-ALL, OTUTTP-shelf-ALL, OTUTTP-shelf-slot-portPsubport";
        type ciena-6500-types:aid;
      }
    }
    output {
      list output {
        leaf otu {
          yang:get-supported "true";
          type ciena-6500-types:IDENT;
          description
            "aid";
        }
        leaf loopback-type {
          yang:get-supported "true";
          type enumeration {
            enum FACILITY {
              description
                "Signal looped toward the equipment";
            }
            enum TERMINAL {
              description
                "Signal looped away from the equipment";
            }
          }
          description
            "Loopback Type";
        }
      }
    }
  }

  rpc port-show-fttp {
    description
      "Retrieve the FTTP facility parameters";
    yang:handler "tl1";
    input {
      leaf fttp {
        mandatory true;
        description
          "AID in format FTTP-shelf-slot-port, FTTP-shelf-slot-ALL, FTTP-shelf-ALL, ALL";
        type ciena-6500-types:aid;
      }
    }
    output {
      list output {
        leaf fttp {
          yang:get-supported "true";
          type ciena-6500-types:IDENT;
          description
            "aid";
        }
        leaf supported-term-pt {
          yang:get-supported "true";
          type ciena-6500-types:aid;
          description
            "The supporting Termination Point.";
        }
        leaf local-sup-cacline-id {
          yang:get-supported "true";
          type ciena-6500-types:STRING;
          description
            "The generic cacline end point representing this facility shown in 54xx nomenclature (<bay>-<A|C>-<slot>-<port>)";
        }
      }
    }
  }

  rpc port-show-sttp {
    description
      "Retrieve the STTP facility parameters";
    yang:handler "tl1";
    input {
      leaf sttp {
        mandatory true;
        description
          "AID in format STTP-shelf-slot-port, STTP-shelf-slotSsubslot-port, STTP-shelf-slotSsubslot-portSsubport, STTP-shelf-slot-portSsubport, STTP-shelf-slot-ALL, STTP-shelf-ALL, ALL";
        type ciena-6500-types:aid;
      }
      leaf stats-info {
        yang:get-supported "true";
        type ciena-6500-enums:StatsInfoDefYes;
        description
          "Specify if Dynamic Status Information is to be included in the response.";
      }
    }
    output {
      list output {
        leaf sttp {
          yang:get-supported "true";
          type ciena-6500-types:IDENT;
          description
            "aid";
        }
        leaf label {
          yang:get-supported "true";
          type string {
            length "0..64";
          }
          description
            "User specified Label";
        }
        leaf rate {
          yang:get-supported "true";
          type ciena-6500-enums:SttpRate;
          description
            "";
        }
        leaf supported-term-pt {
          yang:get-supported "true";
          type ciena-6500-types:aid;
          description
            "The supporting Termination Point.";
        }
        leaf mapping {
          yang:get-supported "true";
          type ciena-6500-enums:SttpMapping;
          description
            "";
        }
        leaf port-mode {
          yang:get-supported "true";
          type ciena-6500-enums:STTPportmode;
          description
            "Optical Port Market Preference";
        }
        leaf sd-th {
          default "6";
          yang:get-supported "true";
          type ciena-6500-types:INT {
            range "5..9";
          }
          description
            "Signal Degrade Threshold value";
        }
        leaf eber-thresh {
          default "3";
          yang:get-supported "true";
          type ciena-6500-types:INT {
            range "3 | 4 | 5";
          }
          description
            "Excessive bit error threshold value";
        }
        leaf exp-trc {
          yang:get-supported "true";
          type string {
            length "0..16";
          }
          description
            "Expected section trace";
        }
        leaf local-sup-cacline-id {
          yang:get-supported "true";
          type ciena-6500-types:STRING;
          description
            "The generic cacline end point representing this facility shown in 54xx nomenclature (<bay>-<A|C>-<slot>-<port>)";
        }
        leaf stformat {
          yang:get-supported "true";
          type ciena-6500-enums:stformat;
          description
            "Section Trace Format";
        }
        leaf tx-trc {
          yang:get-supported "true";
          type ciena-6500-types:STRING;
          description
            "The transmitted Section Trace value";
        }
        leaf rx-trc {
          default "UNKNOWN";
          yang:get-supported "true";
          type ciena-6500-types:STRING;
          description
            "The Received Section Trace value";
        }
        leaf stfmode {
          yang:get-supported "true";
          type ciena-6500-enums:stfmode;
          description
            "Section Trace Fail Mode";
        }
        leaf uneqmode {
          yang:get-supported "true";
          type ciena-6500-enums:uneqmode;
          description
            "Unequipped Insertion Mode";
        }
        leaf rxmon {
          yang:get-supported "true";
          type ciena-6500-enums:BOOL_YES_NO_defaultYES;
          description
            "Indicate if the signal is monitored in the Rx direction for alarms and PMs and OMs.";
        }
        leaf rxterm {
          yang:get-supported "true";
          type ciena-6500-enums:BOOL_YES_NO_defaultYES;
          description
            "Indicate if the signal is terminated in the Rx direction or not.";
        }
        leaf tx-mon {
          yang:get-supported "true";
          type ciena-6500-enums:BOOL_YES_NO_defaultNO;
          description
            "Indicate if the signal is monitored in the Tx direction for alarms and PMs and OMs.";
        }
        leaf tx-term {
          yang:get-supported "true";
          type ciena-6500-enums:BOOL_YES_NO_defaultNO;
          description
            "Indicate if the signal is terminated in the Tx direction for alarms and PMs and OMs.";
        }
        leaf timing-reference {
          yang:get-supported "true";
          type enumeration {
            enum N {
              description
                "Not a timing reference";
            }
            enum Y {
              description
                "Is a timing reference";
            }
          }
          description
            "Indicates whether the facility is being used as a timing reference";
        }
        leaf hold-off {
          default "0";
          yang:get-supported "true";
          type ciena-6500-types:INT {
            range "0 | 10 | 20..1000";
          }
          description
            "Conditioning holdoff timer.";
        }
        leaf pst {
          yang:get-supported "true";
          type ciena-6500-enums:PSTfac_RTRV;
          description
            "Identify the primary State";
        }
        leaf-list sst {
          yang:get-supported "true";
          type ciena-6500-enums:SSTfac;
          description
            "Secondary State";
        }
      }
    }
  }

  rpc port-disable-sttp {
    description
      "Switch STTP Facility Out of Service";
    yang:handler "tl1";
    input {
      leaf sttp {
        mandatory true;
        description
          "AID in format STTP-shelf-slot-port, STTP-shelf-slot-portSsubport, STTP-shelf-slotSsubslot-port";
        type ciena-6500-types:aid;
      }
      leaf sst {
        type ciena-6500-enums:RMVSSTMT;
        description
          "Remove facility from Maintenance State";
      }
    }
  }

  rpc port-enable-sttp {
    description
      "Switch STTP Facility In Service";
    yang:handler "tl1";
    input {
      leaf sttp {
        mandatory true;
        description
          "AID in format STTP-shelf-slot-port, STTP-shelf-slot-portSsubport, STTP-shelf-slotSsubslot-port, STTP-shelf-slotSsubslot-portSsubport";
        type ciena-6500-types:aid;
      }
    }
  }

  rpc port-operate-loopback-sttp {
    description
      "Operate loopback on specified facility.";
    yang:handler "tl1";
    input {
      leaf sttp {
        mandatory true;
        description
          "AID in format STTP-shelf-slot-port, STTP-shelf-slot-portSsubport, STTP-shelf-slotSsubslot-port, STTP-shelf-slotSsubslot-portSsubport";
        type ciena-6500-types:aid;
      }
      leaf loopback-type {
        type enumeration {
          enum FACILITY {
            description
              "Signal looped toward the equipment";
          }
          enum TERMINAL {
            description
              "Signal looped away from the equipment";
          }
        }
        description
          "Loopback Type";
      }
    }
  }

  rpc port-release-loopback-sttp {
    description
      "Release loopback on specified facility.";
    yang:handler "tl1";
    input {
      leaf sttp {
        mandatory true;
        description
          "AID in format STTP-shelf-slot-port, STTP-shelf-slot-portSsubport, STTP-shelf-slotSsubslot-port, STTP-shelf-slotSsubslot-portSsubport";
        type ciena-6500-types:aid;
      }
    }
  }

  rpc port-show-loopback-sttp {
    description
      "Retrieve loopback settings.";
    yang:handler "tl1";
    input {
      leaf sttp {
        mandatory true;
        description
          "AID in format STTP-shelf-slot-port, STTP-shelf-slot-ALL, STTP-shelf-ALL, STTP-shelf-slot-portSsubport, STTP-shelf-slotSsubslot-port, STTP-shelf-slotSsubslot-portSsubport";
        type ciena-6500-types:aid;
      }
    }
    output {
      list output {
        leaf sttp {
          yang:get-supported "true";
          type ciena-6500-types:IDENT;
          description
            "aid";
        }
        leaf loopback-type {
          yang:get-supported "true";
          type enumeration {
            enum FACILITY {
              description
                "Signal looped toward the equipment";
            }
            enum TERMINAL {
              description
                "Signal looped away from the equipment";
            }
          }
          description
            "Loopback Type";
        }
      }
    }
  }

  rpc port-show-ettp {
    description
      "Retrieve the ETTP facility parameters";
    yang:handler "tl1";
    input {
      leaf ettp {
        mandatory true;
        description
          "AID in format ETTP-shelf-slot-port, ETTP-shelf-slot-portSsubport, ETTP-shelf-slot-ALL, ETTP-shelf-ALL, ETTP-shelf-slotSsubslot-portSsubport, ETTP-shelf-slotSsubslot-port, ETTP-shelf-slot-port-rt1Ptp1, ETTP-shelf-slot-port-rt1Ptp1-rt2Ptp2, ETTP-shelf-slot-port-rt1Ptp1-rt2Ptp2-rt3Ptp3, ETTP-shelf-slot-port-rt1Ptp1-rt2Ptp2-rt3Ptp3-rt4Ptp4, ETTP-shelf-slot-port-ALL, ETTP-shelf-slot-portSsubport-rt1Ptp1, ETTP-shelf-slot-portSsubport-rt1Ptp1-rt2Ptp2, ETTP-shelf-slotSsubslot-portSsubport-rt1Ptp1, ETTP-shelf-slotSsubslot-portSsubport-rt1Ptp1-rt2Ptp2, ETTP-shelf-slotSsubslot-port-rt1Ptp1, ETTP-shelf-slotSsubslot-port-rt1Ptp1-rt2Ptp2, ETTP-shelf-slotSsubslot-port-rt1Ptp1-rt2Ptp2-rt3Ptp3, ALL";
        type ciena-6500-types:aid;
      }
      leaf stats-info {
        yang:get-supported "true";
        type ciena-6500-enums:StatsInfoDefYes;
        description
          "Specify if Dynamic Status Information is to be included in the response.";
      }
    }
    output {
      list output {
        leaf ettp {
          yang:get-supported "true";
          type ciena-6500-types:IDENT;
          description
            "aid";
        }
        leaf label {
          yang:get-supported "true";
          type string {
            length "0..64";
          }
          description
            "User specified Label";
        }
        leaf rate {
          yang:get-supported "true";
          type ciena-6500-enums:EthRate;
          description
            "";
        }
        leaf mapping {
          yang:get-supported "true";
          type ciena-6500-enums:EttpMapping;
          description
            "Defines the mapping of this facility and the children that it will have.";
        }
        leaf cond-type {
          yang:get-supported "true";
          type ciena-6500-enums:EttpCondType;
          description
            "Specifies ethernet specific client conditioning behaviour.";
        }
        leaf flow-ctrl {
          yang:get-supported "true";
          type enumeration {
            enum NONE;
            enum ASYM;
            enum PREE;
            enum SYM;
          }
          description
            "Flow control mechanism.";
        }
        leaf hold-off {
          default "100";
          yang:get-supported "true";
          type ciena-6500-types:INT {
            range "0 | 10 | 20..1000";
          }
          description
            "Conditioning holdoff time in seconds.";
        }
        leaf max-transmit-unit {
          yang:get-supported "true";
          type enumeration {
            enum 1600;
            enum 9600;
            enum 2000;
          }
          description
            "Maximum Transmission Unit (actually MRU)";
        }
        leaf supported-term-pt {
          yang:get-supported "true";
          type ciena-6500-types:aid;
          description
            "The supporting Termination Point.";
        }
        leaf mode {
          yang:get-supported "true";
          type enumeration {
            enum TERMINATED;
            enum MONITORED;
          }
          description
            "MAC or PHY layer terminated or monitored";
        }
        leaf local-sup-cacline-id {
          yang:get-supported "true";
          type ciena-6500-types:STRING;
          description
            "The generic cacline end point representing this facility shown in 54xx nomenclature (<bay>-<A|C>-<slot>-<port>)";
        }
        leaf if-type {
          yang:get-supported "true";
          type enumeration {
            enum UNI;
            enum E-NNI;
            enum I-NNI;
          }
          description
            "Interface Type";
        }
        leaf l2-in-use-act {
          yang:get-supported "true";
          type enumeration {
            enum NO {
              description
                "The facility is not used by Layer 2 active configuration ";
            }
            enum YES {
              description
                "The facility is used by Layer 2 active configuration";
            }
          }
          description
            "In use in Layer 2 Active Configuration";
        }
        leaf l2-in-use-sav {
          yang:get-supported "true";
          type enumeration {
            enum NO {
              description
                "The facility is not used by Layer 2 saved configuration ";
            }
            enum YES {
              description
                "The facility is used by Layer 2 saved configuration ";
            }
          }
          description
            "In use in Layer 2 Saved Configuration";
        }
        leaf timing-reference {
          yang:get-supported "true";
          type enumeration {
            enum N {
              description
                "Not a timing reference";
            }
            enum Y {
              description
                "Is a timing reference";
            }
          }
          description
            "Indicates whether the facility is being used as a timing reference";
        }
        leaf service-rate {
          yang:get-supported "true";
          type ciena-6500-types:INT {
            range "0 | 50 | 100..100000";
          }
          description
            "Service rate of the Ethernet Flex in Mbps.";
        }
        leaf transport-rate {
          yang:get-supported "true";
          type ciena-6500-types:INT {
            range "0..104117";
          }
          description
            "Transport rate of the Ethernet Flex in Mbps. The ODUFlex rate.";
        }
        leaf reserved {
          yang:get-supported "true";
          type ciena-6500-enums:BOOL_YES_NO;
          description
            "Specify if the facility is being reserved for packet SNC's";
        }
        leaf rsrvd-oper {
          yang:get-supported "true";
          type ciena-6500-enums:BOOL_YES_NO;
          description
            "Indicates if the reservation is operational for reserved ETTP's";
        }
        leaf fec-frmt {
          yang:get-supported "true";
          type enumeration {
            enum OFF {
              description
                "NO FEC";
            }
            enum RS10 {
              description
                "RS10 FEC";
            }
            enum RS10_KP4 {
              description
                "RS10_KP4 FEC";
            }
          }
          description
            "FEC Format";
        }
        leaf pre-fec-sf-th-lev {
          yang:get-supported "true";
          type ciena-6500-types:STRING;
          description
            "Pre-FEC Signal Fail Threshold Level.";
        }
        leaf pre-fec-sf-th-ber {
          yang:get-supported "true";
          type ciena-6500-types:STRING;
          description
            "Pre-FEC Signal Fail Threshold Bit Error Rate.";
        }
        leaf pre-fec-sd-th-lev {
          yang:get-supported "true";
          type ciena-6500-types:STRING;
          description
            "Pre-FEC Signal Degrade Threshold Level.";
        }
        leaf pre-fec-sd-th-ber {
          yang:get-supported "true";
          type ciena-6500-types:STRING;
          description
            "Pre-FEC Signal Degrade Threshold Bit Error Rate.";
        }
        leaf rx-mon {
          yang:get-supported "true";
          type ciena-6500-enums:BOOL_YES_NO_defaultYES;
          description
            "Indicate if the signal is monitored in the Rx direction for alarms and PMs and OMs.";
        }
        leaf rx-term {
          yang:get-supported "true";
          type ciena-6500-enums:BOOL_YES_NO_defaultYES;
          description
            "Indicate if the signal is terminated in the Rx direction or not.";
        }
        leaf tx-mon {
          yang:get-supported "true";
          type ciena-6500-enums:BOOL_YES_NO_defaultNO;
          description
            "Indicate if the signal is monitored in the Tx direction for alarms and PMs and OMs.";
        }
        leaf tx-term {
          yang:get-supported "true";
          type ciena-6500-enums:BOOL_YES_NO_defaultNO;
          description
            "Indicate if the signal is terminated in the Tx direction for alarms and PMs and OMs.";
        }
        leaf lldpmon {
          yang:get-supported "true";
          type ciena-6500-enums:BOOL_ON_OFF;
          description
            "Specifies if facility is monitoring LLDP packets or not.";
        }
        leaf time-slot-assignment {
          yang:get-supported "true";
          type string {
            length "1..9";
          }
          description
            "Time slots assigned to ETTP.";
        }
        leaf ains-time-left {
          yang:get-supported "true";
          type ciena-6500-types:TIME;
          description
            "The format will be HH-MM for the time left in AINS timeout.";
        }
        leaf pst {
          yang:get-supported "true";
          type ciena-6500-enums:PSTfac_RTRV;
          description
            "Identify the primary State";
        }
        leaf-list sst {
          yang:get-supported "true";
          type ciena-6500-enums:SSTfac;
          description
            "Secondary State";
        }
      }
    }
  }

  rpc port-disable-ettp {
    description
      "Switch ETTP Facility Out of Service";
    yang:handler "tl1";
    input {
      leaf ettp {
        mandatory true;
        description
          "AID in format ETTP-shelf-slot-port, ETTP-shelf-slot-portSsubport, ETTP-shelf-slot-port-rt1Ptp1, ETTP-shelf-slot-portSsubport-rt1Ptp1, ETTP-shelf-slotSsubslot-portSsubport, ETTP-shelf-slotSsubslot-port";
        type ciena-6500-types:aid;
      }
    }
  }

  rpc port-enable-ettp {
    description
      "Switch ETTP Facility In Service";
    yang:handler "tl1";
    input {
      leaf ettp {
        mandatory true;
        description
          "AID in format ETTP-shelf-slot-port, ETTP-shelf-slot-portSsubport, ETTP-shelf-slotSsubslot-portSsubport, ETTP-shelf-slotSsubslot-port, ETTP-shelf-slot-port-rt1Ptp1, ETTP-shelf-slot-portSsubport-rt1Ptp1";
        type ciena-6500-types:aid;
      }
    }
  }

  rpc port-operate-loopback-ettp {
    description
      "Operate loopback on specified facility.";
    yang:handler "tl1";
    input {
      leaf ettp {
        mandatory true;
        description
          "AID in format ETTP-shelf-slot-port, ETTP-shelf-slot-portSsubport, ETTP-shelf-slotSsubslot-portSsubport, ETTP-shelf-slotSsubslot-port";
        type ciena-6500-types:aid;
      }
      leaf loopback-type {
        type enumeration {
          enum FACILITY {
            description
              "Signal looped toward the equipment";
          }
          enum TERMINAL {
            description
              "Signal looped away from the equipment";
          }
        }
        description
          "Loopback Type";
      }
    }
  }

  rpc port-release-loopback-ettp {
    description
      "Release loopback on specified facility.";
    yang:handler "tl1";
    input {
      leaf ettp {
        mandatory true;
        description
          "AID in format ETTP-shelf-slot-port, ETTP-shelf-slot-portSsubport, ETTP-shelf-slotSsubslot-portSsubport, ETTP-shelf-slotSsubslot-port";
        type ciena-6500-types:aid;
      }
    }
  }

  rpc port-show-loopback-ettp {
    description
      "Retrieve loopback settings.";
    yang:handler "tl1";
    input {
      leaf ettp {
        mandatory true;
        description
          "AID in format ETTP-shelf-slot-port, ETTP-shelf-slot-portSsubport, ETTP-shelf-slotSsubslot-portSsubport, ETTP-shelf-slotSsubslot-port, ETTP-shelf-slot-ALL, ETTP-shelf-ALL";
        type ciena-6500-types:aid;
      }
    }
    output {
      list output {
        leaf ettp {
          yang:get-supported "true";
          type ciena-6500-types:IDENT;
          description
            "aid";
        }
        leaf loopback-type {
          yang:get-supported "true";
          type enumeration {
            enum FACILITY {
              description
                "Signal looped toward the equipment";
            }
            enum TERMINAL {
              description
                "Signal looped away from the equipment";
            }
          }
          description
            "Loopback Type";
        }
      }
    }
  }

  rpc port-show-msi-oduttp {
    description
      "Retrieve MSI values for the ODUTTP facility.";
    yang:handler "tl1";
    input {
      leaf oduttp {
        mandatory true;
        description
          "AID in format ODUTTP-shelf-slot-port-rt1Ptp1, ODUTTP-shelf-slot-port-rt1Ptp1-rt2Ptp2, ODUTTP-shelf-slot-port-rt1Ptp1-rt2Ptp2-rt3Ptp3, ODUTTP-shelf-slot-port-rt1Ptp1-rt2Ptp2-rt3Ptp3-rt4Ptp4, ODUTTP-shelf-slot-portSsubport-rt1Ptp1, ODUTTP-shelf-slot-portSsubport-rt1Ptp1-rt2Ptp2, ODUTTP-shelf-slot-portPsubport-rt1Ptp1-rt2Ptp2, ODUTTP-shelf-slot-portPsubport-rt1Ptp1, ODUTTP-shelf-slot-port-rt1Ptp1-ALL, ODUTTP-shelf-slot-port-ALL, ODUTTP-shelf-slot-ALL, ODUTTP-shelf-slot-portPsubport-ALL, ODUTTP-shelf-slot-port-rt1Ptp1-rt2Ptp2-rt3Ptp3-ALL, ODUTTP-shelf-slot-port-rt1Ptp1-rt2Ptp2-ALL, ODUTTP-shelf-ALL, ODUTTP-shelf-slot-portSsubport-ALL, ODUTTP-shelf-slotSsubslot-port-rt1Ptp1, ODUTTP-shelf-slotSsubslot-portSsubport-rt1Ptp1, ODUTTP-shelf-slotSsubslot-portSsubport-rt1Ptp1-rt2Ptp2, ODUTTP-shelf-slotSsubslot-port-rt1Ptp1-rt2Ptp2, ODUTTP-shelf-slotSsubslot-port-rt1Ptp1-rt2Ptp2-rt3Ptp3, ALL";
        type ciena-6500-types:aid;
      }
      leaf-list msi-type {
        yang:get-supported "true";
        type ciena-6500-enums:msiType;
        description
          "Specify the type of MSI information to be included in the response.";
      }
    }
    output {
      list output {
        leaf oduttp {
          yang:get-supported "true";
          type ciena-6500-types:IDENT;
          description
            "aid";
        }
        leaf prov-msi1 {
          yang:get-supported "true";
          type string {
            length "1..200";
          }
          description
            "Provisioned MSI for OPUC #1.";
        }
        leaf prov-msi2 {
          yang:get-supported "true";
          type string {
            length "1..100";
          }
          description
            "Provisioned MSI for OPUC #2.";
        }
        leaf prov-msi3 {
          yang:get-supported "true";
          type string {
            length "1..100";
          }
          description
            "Provisioned MSI for OPUC #3.";
        }
        leaf prov-msi4 {
          yang:get-supported "true";
          type string {
            length "1..100";
          }
          description
            "Provisioned MSI for OPUC #4.";
        }
        leaf prov-msi5 {
          yang:get-supported "true";
          type string {
            length "1..100";
          }
          description
            "Provisioned MSI for OPUC #5.";
        }
        leaf prov-msi6 {
          yang:get-supported "true";
          type string {
            length "1..100";
          }
          description
            "Provisioned MSI for OPUC #6.";
        }
        leaf prov-msi7 {
          yang:get-supported "true";
          type string {
            length "1..100";
          }
          description
            "Provisioned MSI for OPUC #7.";
        }
        leaf prov-msi8 {
          yang:get-supported "true";
          type string {
            length "1..100";
          }
          description
            "Provisioned MSI for OPUC #8.";
        }
        leaf prov-msi9 {
          yang:get-supported "true";
          type string {
            length "1..100";
          }
          description
            "Provisioned MSI for OPUC #9.";
        }
        leaf prov-msi10 {
          yang:get-supported "true";
          type string {
            length "1..100";
          }
          description
            "Provisioned MSI for OPUC #10.";
        }
        leaf prov-msi11 {
          yang:get-supported "true";
          type string {
            length "1..100";
          }
          description
            "Provisioned MSI for OPUC #11.";
        }
        leaf prov-msi12 {
          yang:get-supported "true";
          type string {
            length "1..100";
          }
          description
            "Provisioned MSI for OPUC #12.";
        }
        leaf prov-msi13 {
          yang:get-supported "true";
          type string {
            length "1..100";
          }
          description
            "Provisioned MSI for OPUC #13.";
        }
        leaf prov-msi14 {
          yang:get-supported "true";
          type string {
            length "1..100";
          }
          description
            "Provisioned MSI for OPUC #14.";
        }
        leaf prov-msi15 {
          yang:get-supported "true";
          type string {
            length "1..100";
          }
          description
            "Provisioned MSI for OPUC #15.";
        }
        leaf prov-msi16 {
          yang:get-supported "true";
          type string {
            length "1..100";
          }
          description
            "Provisioned MSI for OPUC #16.";
        }
        leaf rx-msi1 {
          yang:get-supported "true";
          type string {
            length "1..200";
          }
          description
            "Actual received MSI for OPUC #1.";
        }
        leaf rx-msi2 {
          yang:get-supported "true";
          type string {
            length "1..100";
          }
          description
            "Actual received MSI for OPUC #2.";
        }
        leaf rx-msi3 {
          yang:get-supported "true";
          type string {
            length "1..100";
          }
          description
            "Actual received MSI for OPUC #3.";
        }
        leaf rx-msi4 {
          yang:get-supported "true";
          type string {
            length "1..100";
          }
          description
            "Actual received MSI for OPUC #4.";
        }
        leaf rx-msi5 {
          yang:get-supported "true";
          type string {
            length "1..100";
          }
          description
            "Actual received MSI for OPUC #5.";
        }
        leaf rx-msi6 {
          yang:get-supported "true";
          type string {
            length "1..100";
          }
          description
            "Actual received MSI for OPUC #6.";
        }
        leaf rx-msi7 {
          yang:get-supported "true";
          type string {
            length "1..100";
          }
          description
            "Actual received MSI for OPUC #7.";
        }
        leaf rx-msi8 {
          yang:get-supported "true";
          type string {
            length "1..100";
          }
          description
            "Actual received MSI for OPUC #8.";
        }
        leaf rx-msi9 {
          yang:get-supported "true";
          type string {
            length "1..100";
          }
          description
            "Actual received MSI for OPUC #9.";
        }
        leaf rx-msi10 {
          yang:get-supported "true";
          type string {
            length "1..100";
          }
          description
            "Actual received MSI for OPUC #10.";
        }
        leaf rx-msi11 {
          yang:get-supported "true";
          type string {
            length "1..100";
          }
          description
            "Actual received MSI for OPUC #11.";
        }
        leaf rx-msi12 {
          yang:get-supported "true";
          type string {
            length "1..100";
          }
          description
            "Actual received MSI for OPUC #12.";
        }
        leaf rx-msi13 {
          yang:get-supported "true";
          type string {
            length "1..100";
          }
          description
            "Actual received MSI for OPUC #13.";
        }
        leaf rx-msi14 {
          yang:get-supported "true";
          type string {
            length "1..100";
          }
          description
            "Actual received MSI for OPUC #14.";
        }
        leaf rx-msi15 {
          yang:get-supported "true";
          type string {
            length "1..100";
          }
          description
            "Actual received MSI for OPUC #15.";
        }
        leaf rx-msi16 {
          yang:get-supported "true";
          type string {
            length "1..100";
          }
          description
            "Actual received MSI for OPUC #16.";
        }
      }
    }
  }

  rpc port-show-oduttp {
    description
      "Retrieve the ODUTTP facility parameters";
    yang:handler "tl1";
    input {
      leaf oduttp {
        mandatory true;
        description
          "AID in format ODUTTP-shelf-slot-port-rt1Ptp1, ODUTTP-shelf-slot-port-rt1Ptp1-rt2Ptp2, ODUTTP-shelf-slot-port-rt1Ptp1-rt2Ptp2-rt3Ptp3, ODUTTP-shelf-slot-port-rt1Ptp1-rt2Ptp2-rt3Ptp3-rt4Ptp4, ODUTTP-shelf-slot-portSsubport-rt1Ptp1, ODUTTP-shelf-slot-portSsubport-rt1Ptp1-rt2Ptp2, ODUTTP-shelf-slot-portPsubport-rt1Ptp1-rt2Ptp2, ODUTTP-shelf-slot-portPsubport-rt1Ptp1, ODUTTP-shelf-slot-port-rt1Ptp1-ALL, ODUTTP-shelf-slot-port-ALL, ODUTTP-shelf-slot-ALL, ODUTTP-shelf-slot-portPsubport-ALL, ODUTTP-shelf-slot-port-rt1Ptp1-rt2Ptp2-rt3Ptp3-ALL, ODUTTP-shelf-slot-port-rt1Ptp1-rt2Ptp2-ALL, ODUTTP-shelf-ALL, ODUTTP-shelf-slot-portSsubport-ALL, ODUTTP-shelf-slotSsubslot-port-rt1Ptp1, ODUTTP-shelf-slotSsubslot-portSsubport-rt1Ptp1, ODUTTP-shelf-slotSsubslot-portSsubport-rt1Ptp1-rt2Ptp2, ODUTTP-shelf-slotSsubslot-port-rt1Ptp1-rt2Ptp2, ODUTTP-shelf-slotSsubslot-port-rt1Ptp1-rt2Ptp2-rt3Ptp3, ALL";
        type ciena-6500-types:aid;
      }
      leaf stats-info {
        yang:get-supported "true";
        type ciena-6500-enums:StatsInfoDefNo;
        description
          "Specify if Dynamic Status Information is to be included in the response.";
      }
    }
    output {
      list output {
        leaf oduttp {
          yang:get-supported "true";
          type ciena-6500-types:IDENT;
          description
            "aid";
        }
        leaf rate {
          yang:get-supported "true";
          type ciena-6500-enums:OduTtpRate;
          description
            "Rate";
        }
        leaf trib-slot-assignment {
          yang:get-supported "true";
          type string {
            length "1..99";
          }
          description
            "The tributary slots used by this ODU.";
        }
        leaf num-ts {
          default "1";
          yang:get-supported "true";
          type ciena-6500-types:INT {
            range "1..320";
          }
          description
            "Used to identify the number of tributaries comprising this TTP. For on OTN TTP, this can change based on potential configuration of desired payload type (e.g. for ODU1 with OPVC payload, this value is 16; with CBR it is 1).";
        }
        leaf ts-size {
          yang:get-supported "true";
          type enumeration {
            enum ODU0 {
              description
                "ODU0 is the tributary slot size (unit)";
            }
            enum ODU1 {
              description
                "ODU1 is the tributary slot size (unit)";
            }
          }
          description
            "The tributary slot size";
        }
        leaf label {
          yang:get-supported "true";
          type string {
            length "0..64";
          }
          description
            "User specified Label";
        }
        leaf tx-sapi {
          yang:get-supported "true";
          type string {
            length "0..15";
          }
          description
            "The Source Access Point Identifier (SAPI), provisioned by the managing system at the termination source, to be placed in the Trail Trace Identifier (TTI) overhead position of the source of a trail.";
        }
        leaf tx-dapi {
          yang:get-supported "true";
          type string {
            length "0..15";
          }
          description
            "The Destination Access Point Identifier (DAPI), provisioned by the managing system at the termination source, to be placed in the Trail Trace Identifier (TTI) overhead position of the source of a trail.";
        }
        leaf tx-oper {
          yang:get-supported "true";
          type string {
            length "0..32";
          }
          description
            "The operator specific part of the Trail Trace Identifier (TTI) information, provisioned by the managing system at the termination source, to be placed in the TTI overhead position of the source of a trail.";
        }
        leaf ex-sapi {
          yang:get-supported "true";
          type string {
            length "0..15";
          }
          description
            "The expected Source Access Point Identifier (SAPI), provisioned by the managing system, to be compared with the received SAPI at the overhead position of the sink for the purpose of checking the integrity of connectivity. ";
        }
        leaf ex-dapi {
          yang:get-supported "true";
          type string {
            length "0..15";
          }
          description
            "The expected Destination Access Point Identifier (DAPI), provisioned by the managing system, to be compared with the received DAPI at the overhead position of the sink for the purpose of checking the integrity of connectivity. ";
        }
        leaf ex-oper {
          yang:get-supported "true";
          type string {
            length "0..32";
          }
          description
            "The expected operator specific part of the Trail Trace Identifier (TTI) information, provisioned by the managing system at the termination source, to be placed in the TTI overhead position of the source of a trail.";
        }
        leaf rx-sapi {
          yang:get-supported "true";
          type string {
            length "0..15";
          }
          description
            "The Source Access Point Identifier (SAPI) recovered from the Trail Trace Identifier (TTI) overhead position at the sink of a trail.";
        }
        leaf rx-dapi {
          yang:get-supported "true";
          type string {
            length "0..15";
          }
          description
            "The Destination Access Point Identifier (DAPI) recovered from the Trail Trace Identifier (TTI) overhead position at the sink of a trail.";
        }
        leaf rx-oper {
          yang:get-supported "true";
          type string {
            length "0..32";
          }
          description
            "The operator specific part of the Trail Trace Identifier (TTI) information, recovered from the TTI overhead position at the sink of a trail.";
        }
        leaf ex-pt {
          yang:get-supported "true";
          type string {
            length "2";
          }
          description
            "The expected payload type.";
        }
        leaf rx-pt {
          yang:get-supported "true";
          type string {
            length "2";
          }
          description
            "The received payload type.";
        }
        leaf tf-mode {
          yang:get-supported "true";
          type ciena-6500-enums:otntfMode;
          description
            "Trace Fail Mode";
        }
        leaf tim-enable {
          yang:get-supported "true";
          type enumeration {
            enum TIM_SAPI_ONLY {
              description
                "Only checks for SAPI mismatch";
            }
            enum TIM_DAPI_ONLY {
              description
                "Only checks for DAPI mismatch";
            }
            enum TIM_SAPI_DAPI {
              description
                "Checks for SAPI and DAPI mismatch";
            }
            enum TIM_OPER_SPEC {
              description
                "Checks for Operator Specific mismatch";
            }
          }
          description
            "The Trail Trace Identifier Mismatch (TIM) controls checking for Trace Identifier Mismatch fault detection. ";
        }
        leaf-list cond-type {
          yang:get-supported "true";
          type ciena-6500-enums:OduCtpCondType;
          description
            "Conditioning behaviour on client faults. ";
        }
        leaf dm-count {
          yang:get-supported "true";
          type ciena-6500-types:STRING;
          description
            "Value of delay measurement of ODU in micro seconds.";
        }
        leaf line-prot-group {
          yang:get-supported "true";
          type ciena-6500-types:aid;
          description
            "Line Protection Group in AID format";
        }
        leaf line-prot-role {
          yang:get-supported "true";
          type enumeration {
            enum UNPROTECTED;
            enum WORK;
            enum PROTECT;
            enum WORK_PROTECT;
          }
          description
            "Line Protection Role";
        }
        leaf line-prot-type {
          yang:get-supported "true";
          type enumeration {
            enum NOT_PROTECTED;
            enum APS_PROTECTED;
          }
          description
            "Line Protection Type";
        }
        leaf owner {
          yang:get-supported "true";
          type ciena-6500-enums:Owner;
          description
            "Specifies who created this TTP.";
        }
        leaf supported-term-pt {
          yang:get-supported "true";
          type ciena-6500-types:aid;
          description
            "The supporting Termination Point.";
        }
        leaf client-type {
          yang:get-supported "true";
          type ciena-6500-enums:clientTypeTtp;
          description
            "Server layer client type";
        }
        leaf dm-enable {
          yang:get-supported "true";
          type ciena-6500-enums:BOOL_YES_NO;
          description
            "Specify if delay measurement is enable.";
        }
        leaf odu1-interop {
          yang:get-supported "true";
          type enumeration {
            enum OTHER {
              description
                "Interop with equipment other than 2G5 MOTR";
            }
            enum 2G5MOTR {
              description
                "Interop with equipment 2G5 MOTR";
            }
          }
          description
            "Required Interop Equipment Type";
        }
        leaf rx-ts-mode {
          yang:get-supported "true";
          type ciena-6500-enums:rxtsMode;
          description
            "Receive Tributary Slot Mode";
        }
        leaf rx-ts {
          yang:get-supported "true";
          type string {
            length "1..99";
          }
          description
            "Received tributary slots.";
        }
        leaf ex-rx-ts {
          yang:get-supported "true";
          type string {
            length "1..99";
          }
          description
            "Expected Receive tributary slots.";
        }
        leaf flex-type {
          yang:get-supported "true";
          type ciena-6500-enums:flexType;
          description
            "ODU flex type";
        }
        leaf resizeable {
          yang:get-supported "true";
          type ciena-6500-enums:BOOL_YES_NO;
          description
            "ODUFlex is resizeable";
        }
        leaf base-ho {
          yang:get-supported "true";
          type ciena-6500-enums:baseHO;
          description
            "Base HO ODUk";
        }
        leaf bit-rate {
          yang:get-supported "true";
          type string {
            length "0..19";
          }
          description
            "Define the bit rate of flex.";
        }
        leaf tolerance {
          yang:get-supported "true";
          type string {
            length "0..64";
          }
          description
            "Define the tolerance in ppm of oduflex payload.";
        }
        leaf local-sup-cacline-id {
          yang:get-supported "true";
          type ciena-6500-types:STRING;
          description
            "The generic cacline end point representing this facility shown in 54xx nomenclature (<bay>-<A|C>-<slot>-<port>)";
        }
        leaf anchor-ts {
          yang:get-supported "true";
          type ciena-6500-types:INT {
            range "1..80";
          }
          description
            "Anchor of tx triburtary slot";
        }
        leaf trib-slot-prov {
          yang:get-supported "true";
          type ciena-6500-enums:TsProv;
          description
            "tribSlot provision";
        }
        leaf sd-th {
          yang:get-supported "true";
          type ciena-6500-types:INT {
            range "5..9";
          }
          description
            "Signal Degrade Threshold Value";
        }
        leaf sf-th {
          yang:get-supported "true";
          type ciena-6500-types:INT {
            range "0..9";
          }
          description
            "Signal Fail Threshold Level.";
        }
        leaf prov-msi {
          yang:get-supported "true";
          type string {
            length "1..1600";
          }
          description
            "Provisioned MSI for all tributary slots.";
        }
        leaf rx-msi {
          yang:get-supported "true";
          type string {
            length "1..1600";
          }
          description
            "Actual received MSI for all tributary slots.";
        }
        leaf timing-reference {
          yang:get-supported "true";
          type enumeration {
            enum N {
              description
                "Not a timing reference";
            }
            enum Y {
              description
                "Is a timing reference";
            }
          }
          description
            "Indicates whether the facility is being used as a timing reference";
        }
        leaf reserved {
          yang:get-supported "true";
          type ciena-6500-enums:BOOL_YES_NO;
          description
            "Specify if the facility is being reserved for packet SNC's";
        }
        leaf act-avail-ts {
          yang:get-supported "true";
          type string {
            length "1..320";
          }
          description
            "Actual available TS supported by the TRANSMODE.";
        }
        leaf rxmon {
          yang:get-supported "true";
          type ciena-6500-enums:BOOL_YES_NO_defaultNO;
          description
            "Indicate if the signal is monitored in the Rx direction for alarms and PMs and OMs.";
        }
        leaf rxterm {
          yang:get-supported "true";
          type ciena-6500-enums:BOOL_YES_NO_defaultNO;
          description
            "Indicate if the signal is terminated in the Rx direction or not.";
        }
        leaf tx-mon {
          yang:get-supported "true";
          type ciena-6500-enums:BOOL_YES_NO_defaultNO;
          description
            "Indicate if the signal is monitored in the Tx direction for alarms and PMs and OMs.";
        }
        leaf tx-term {
          yang:get-supported "true";
          type ciena-6500-enums:BOOL_YES_NO_defaultNO;
          description
            "Indicate if the signal is terminated in the Tx direction for alarms and PMs and OMs.";
        }
        leaf degm-intv {
          yang:get-supported "true";
          type ciena-6500-types:INT {
            range "2..10";
          }
          description
            "Consecutive bad intervals required to declare signal degrade";
        }
        leaf degthr-percentage {
          yang:get-supported "true";
          type ciena-6500-types:INT {
            range "1..1000";
          }
          description
            "Percentage of errored blocks required to declare an interval bad";
        }
        leaf gcc1-mode {
          yang:get-supported "true";
          type ciena-6500-enums:GCCMode;
          description
            "GCC1 Aggregation mode";
        }
        leaf gcc2-mode {
          yang:get-supported "true";
          type ciena-6500-enums:GCCMode;
          description
            "GCC2 Aggregation mode";
        }
        leaf pst {
          yang:get-supported "true";
          type ciena-6500-enums:PSTfac_RTRV;
          description
            "Identify the primary State";
        }
        leaf-list sst {
          yang:get-supported "true";
          type ciena-6500-enums:SSTfac;
          description
            "Secondary State";
        }
      }
    }
  }

  rpc port-disable-oduttp {
    description
      "Switch ODUTTP Facility Out of Service";
    yang:handler "tl1";
    input {
      leaf oduttp {
        mandatory true;
        description
          "AID in format ODUTTP-shelf-slot-port-rt1Ptp1, ODUTTP-shelf-slot-port-rt1Ptp1-rt2Ptp2, ODUTTP-shelf-slot-port-rt1Ptp1-rt2Ptp2-rt3Ptp3, ODUTTP-shelf-slot-port-rt1Ptp1-rt2Ptp2-rt3Ptp3-rt4Ptp4, ODUTTP-shelf-slot-portSsubport-rt1Ptp1, ODUTTP-shelf-slot-portSsubport-rt1Ptp1-rt2Ptp2, ODUTTP-shelf-slotSsubslot-portSsubport-rt1Ptp1, ODUTTP-shelf-slotSsubslot-portSsubport-rt1Ptp1-rt2Ptp2, ODUTTP-shelf-slotSsubslot-port-rt1Ptp1, ODUTTP-shelf-slotSsubslot-port-rt1Ptp1-rt2Ptp2, ODUTTP-shelf-slotSsubslot-port-rt1Ptp1-rt2Ptp2-rt3Ptp3, ODUTTP-shelf-slot-portPsubport-rt1Ptp1, ODUTTP-shelf-slot-portPsubport-rt1Ptp1-rt2Ptp2";
        type ciena-6500-types:aid;
      }
    }
  }

  rpc port-enable-oduttp {
    description
      "Switch ODUTTP Facility In Service";
    yang:handler "tl1";
    input {
      leaf oduttp {
        mandatory true;
        description
          "AID in format ODUTTP-shelf-slot-port-rt1Ptp1, ODUTTP-shelf-slot-port-rt1Ptp1-rt2Ptp2, ODUTTP-shelf-slot-port-rt1Ptp1-rt2Ptp2-rt3Ptp3, ODUTTP-shelf-slot-port-rt1Ptp1-rt2Ptp2-rt3Ptp3-rt4Ptp4, ODUTTP-shelf-slot-portSsubport-rt1Ptp1, ODUTTP-shelf-slot-portSsubport-rt1Ptp1-rt2Ptp2, ODUTTP-shelf-slot-portPsubport-rt1Ptp1, ODUTTP-shelf-slotSsubslot-port-rt1Ptp1, ODUTTP-shelf-slot-portPsubport-rt1Ptp1-rt2Ptp2";
        type ciena-6500-types:aid;
      }
    }
  }

  rpc port-operate-loopback-oduttp {
    description
      "Operate loopback on specified facility.";
    yang:handler "tl1";
    input {
      leaf oduttp {
        mandatory true;
        description
          "AID in format ODUTTP-shelf-slot-port-rt1Ptp1, ODUTTP-shelf-slot-port-rt1Ptp1-rt2Ptp2";
        type ciena-6500-types:aid;
      }
      leaf loopback-type {
        type enumeration {
          enum FACILITY {
            description
              "Signal looped toward the equipment";
          }
          enum TERMINAL {
            description
              "Signal looped away from the equipment";
          }
        }
        default "FACILITY";
        description
          "Loopback Type";
      }
    }
  }

  rpc port-release-loopback-oduttp {
    description
      "Release loopback on specified facility.";
    yang:handler "tl1";
    input {
      leaf oduttp {
        mandatory true;
        description
          "AID in format ODUTTP-shelf-slot-port-rt1Ptp1, ODUTTP-shelf-slot-port-rt1Ptp1-rt2Ptp2";
        type ciena-6500-types:aid;
      }
    }
  }

  rpc port-show-loopback-oduttp {
    description
      "Retrieve loopback settings.";
    yang:handler "tl1";
    input {
      leaf oduttp {
        mandatory true;
        description
          "AID in format ODUTTP-shelf-slot-port-rt1Ptp1, ODUTTP-shelf-slot-port-rt1Ptp1-rt2Ptp2, ODUTTP-shelf-slot-port-rt1Ptp1-ALL, ODUTTP-shelf-slot-port-ALL, ODUTTP-shelf-slot-ALL, ODUTTP-shelf-ALL";
        type ciena-6500-types:aid;
      }
    }
    output {
      list output {
        leaf oduttp {
          yang:get-supported "true";
          type ciena-6500-types:IDENT;
          description
            "aid";
        }
        leaf loopback-type {
          yang:get-supported "true";
          type enumeration {
            enum FACILITY {
              description
                "Signal looped toward the equipment";
            }
            enum TERMINAL {
              description
                "Signal looped away from the equipment";
            }
          }
          description
            "Loopback Type";
        }
      }
    }
  }

  rpc port-show-oductp {
    description
      "Retrieve the ODUCTP facility parameters";
    yang:handler "tl1";
    input {
      leaf oductp {
        mandatory true;
        description
          "AID in format ODUCTP-shelf-slot-port-rt1Ptp1, ODUCTP-shelf-slot-port-rt1Ptp1-rt2Ptp2, ODUCTP-shelf-slot-port-rt1Ptp1-rt2Ptp2-rt3Ptp3, ODUCTP-shelf-slot-port-rt1Ptp1-rt2Ptp2-rt3Ptp3-rt4Ptp4, ODUCTP-shelf-slot-portPsubport-rt1Ptp1-rt2Ptp2-rt3Ptp3, ODUCTP-shelf-slot-portSsubport-rt1Ptp1, ODUCTP-shelf-slot-portSsubport-rt1Ptp1-rt2Ptp2, ODUCTP-shelf-slot-port-rt1Ptp1-rt2Ptp2-rt3Ptp3-rt4Ptp4-ALL, ODUCTP-shelf-slot-port-rt1Ptp1-rt2Ptp2-rt3Ptp3-ALL, ODUCTP-shelf-slot-port-rt1Ptp1-rt2Ptp2-ALL, ODUCTP-shelf-slot-port-rt1Ptp1-ALL, ODUCTP-shelf-slot-port-ALL, ODUCTP-shelf-slot-ALL, ODUCTP-shelf-ALL, ODUCTP-shelf-slot-portPsubport-ALL, ODUCTP-shelf-slot-portSsubport-ALL, ODUCTP-shelf-slot-portPsubport-rt1Ptp1-ALL, ODUCTP-shelf-slot-portPsubport-rt1Ptp1-rt2Ptp2, ODUCTP-shelf-slot-portPsubport-rt1Ptp1, ODUCTP-shelf-slotSsubslot-portSsubport-rt1Ptp1, ODUCTP-shelf-slotSsubslot-portSsubport-rt1Ptp1-rt2Ptp2, ODUCTP-shelf-slotSsubslot-port-rt1Ptp1, ODUCTP-shelf-slotSsubslot-port-rt1Ptp1-rt2Ptp2, ODUCTP-shelf-slotSsubslot-port-rt1Ptp1-rt2Ptp2-rt3Ptp3, ODUCTP-shelf-slotSsubslot-port-rt1Ptp1-rt2Ptp2-rt3Ptp3-rt4Ptp4, ALL";
        type ciena-6500-types:aid;
      }
      leaf stats-info {
        yang:get-supported "true";
        type ciena-6500-enums:StatsInfoDefNo;
        description
          "Specify if Dynamic Status Information is to be included in the response.";
      }
    }
    output {
      list output {
        leaf oductp {
          yang:get-supported "true";
          type ciena-6500-types:IDENT;
          description
            "aid";
        }
        leaf rate {
          yang:get-supported "true";
          type ciena-6500-enums:OduCtpRate;
          description
            "Rate";
        }
        leaf ctp-mode {
          yang:get-supported "true";
          type enumeration {
            enum TRANSPARENT;
            enum MONITOR;
            enum TERMINATED;
          }
          description
            "The mode of the ODUCTP.";
        }
        leaf trib-slot-assignment {
          yang:get-supported "true";
          type string {
            length "1..99";
          }
          description
            "The tributary slots used by this ODU.";
        }
        leaf num-ts {
          yang:get-supported "true";
          type ciena-6500-types:INT {
            range "1..320";
          }
          description
            "Used to identify the number of tributaries comprising this CTP.";
        }
        leaf label {
          yang:get-supported "true";
          type string {
            length "0..64";
          }
          description
            "User specified Label";
        }
        leaf tx-sapi {
          yang:get-supported "true";
          type string {
            length "0..15";
          }
          description
            "The Source Access Point Identifier (SAPI), provisioned by the managing system at the termination source, to be placed in the Trail Trace Identifier (TTI) overhead position of the source of a trail.";
        }
        leaf tx-dapi {
          yang:get-supported "true";
          type string {
            length "0..15";
          }
          description
            "The Destination Access Point Identifier (DAPI), provisioned by the managing system at the termination source, to be placed in the Trail Trace Identifier (TTI) overhead position of the source of a trail.";
        }
        leaf tx-oper {
          yang:get-supported "true";
          type string {
            length "0..32";
          }
          description
            "The operator specific part of the Trail Trace Identifier (TTI) information, provisioned by the managing system at the termination source, to be placed in the TTI overhead position of the source of a trail.";
        }
        leaf ex-sapi {
          yang:get-supported "true";
          type string {
            length "0..15";
          }
          description
            "The expected Source Access Point Identifier (SAPI), provisioned by the managing system, to be compared with the received SAPI at the overhead position of the sink for the purpose of checking the integrity of connectivity. ";
        }
        leaf ex-dapi {
          yang:get-supported "true";
          type string {
            length "0..15";
          }
          description
            "The expected Destination Access Point Identifier (DAPI), provisioned by the managing system, to be compared with the received DAPI at the overhead position of the sink for the purpose of checking the integrity of connectivity. ";
        }
        leaf ex-oper {
          yang:get-supported "true";
          type string {
            length "0..32";
          }
          description
            "The expected operator specific part of the Trail Trace Identifier (TTI) information, provisioned by the managing system at the termination source, to be placed in the TTI overhead position of the source of a trail.";
        }
        leaf rx-sapi {
          yang:get-supported "true";
          type string {
            length "0..15";
          }
          description
            "The Source Access Point Identifier (SAPI) recovered from the Trail Trace Identifier (TTI) overhead position at the sink of a trail.";
        }
        leaf rx-dapi {
          yang:get-supported "true";
          type string {
            length "0..15";
          }
          description
            "The Destination Access Point Identifier (DAPI) recovered from the Trail Trace Identifier (TTI) overhead position at the sink of a trail.";
        }
        leaf rx-oper {
          yang:get-supported "true";
          type string {
            length "0..32";
          }
          description
            "The operator specific part of the Trail Trace Identifier (TTI) information, recovered from the TTI overhead position at the sink of a trail.";
        }
        leaf ex-pt {
          yang:get-supported "true";
          type string {
            length "2";
          }
          description
            "The expected payload type.";
        }
        leaf rx-pt {
          yang:get-supported "true";
          type string {
            length "2";
          }
          description
            "The received payload type.";
        }
        leaf tf-mode {
          yang:get-supported "true";
          type ciena-6500-enums:otntfMode;
          description
            "Trace Fail Mode";
        }
        leaf tim-enable {
          yang:get-supported "true";
          type enumeration {
            enum TIM_SAPI_ONLY {
              description
                "Only checks for SAPI mismatch";
            }
            enum TIM_DAPI_ONLY {
              description
                "Only checks for DAPI mismatch";
            }
            enum TIM_SAPI_DAPI {
              description
                "Checks for SAPI and DAPI mismatch";
            }
            enum TIM_OPER_SPEC {
              description
                "Checks for Operator Specific mismatch";
            }
          }
          description
            "The Trail Trace Identifier Mismatch (TIM) controls checking for Trace Identifier Mismatch fault detection. ";
        }
        leaf-list cond-type {
          yang:get-supported "true";
          type ciena-6500-enums:OduCtpCondType;
          description
            "Conditioning behaviour on client faults. ";
        }
        leaf dm-count {
          yang:get-supported "true";
          type ciena-6500-types:STRING;
          description
            "Value of delay measurement of ODU in micro seconds.";
        }
        leaf owner {
          yang:get-supported "true";
          type ciena-6500-enums:Owner;
          description
            "Specifies who created this CTP.";
        }
        leaf supported-term-pt {
          yang:get-supported "true";
          type ciena-6500-types:aid;
          description
            "The supporting Termination Point.";
        }
        leaf dm-enable {
          yang:get-supported "true";
          type ciena-6500-enums:BOOL_YES_NO;
          description
            "Specify if delay measurement is enable.";
        }
        leaf rx-ts-mode {
          yang:get-supported "true";
          type ciena-6500-enums:rxtsMode;
          description
            "Received Tributary Slot Mode";
        }
        leaf rx-ts {
          yang:get-supported "true";
          type string {
            length "1..99";
          }
          description
            "Received tributary slots.";
        }
        leaf ex-rx-ts {
          yang:get-supported "true";
          type string {
            length "1..99";
          }
          description
            "Expected receive tributary slots.";
        }
        leaf flex-type {
          yang:get-supported "true";
          type ciena-6500-enums:flexType;
          description
            "ODU flex type";
        }
        leaf resizeable {
          yang:get-supported "true";
          type ciena-6500-enums:BOOL_YES_NO;
          description
            "ODUFlex is resizeable";
        }
        leaf base-ho {
          yang:get-supported "true";
          type ciena-6500-enums:baseHO;
          description
            "Base HO ODUk";
        }
        leaf client-type {
          yang:get-supported "true";
          type ciena-6500-enums:clientTypeCtp;
          description
            "Indicate the type of client signal";
        }
        leaf bit-rate {
          yang:get-supported "true";
          type string {
            length "0..19";
          }
          description
            "Define the bit rate of flex.";
        }
        leaf tolerance {
          yang:get-supported "true";
          type string {
            length "0..64";
          }
          description
            "Define the tolerance in ppm of oduflex payload.";
        }
        leaf gep {
          yang:get-supported "true";
          type enumeration {
            enum YES;
            enum NO;
          }
          description
            "Specifies whether the end-point facility accepts Generict End Point (GEP) method.";
        }
        leaf gep-name {
          yang:get-supported "true";
          type string {
            length "1..64";
          }
          description
            "Specifies the Generict End Point (GEP) name for this facility.";
        }
        leaf trib-slot-prov {
          yang:get-supported "true";
          type ciena-6500-enums:TsProv;
          description
            "tribSlot provision";
        }
        leaf sd-th {
          yang:get-supported "true";
          type ciena-6500-types:INT {
            range "6..9";
          }
          description
            "Signal degrade threshold value";
        }
        leaf sf-th {
          yang:get-supported "true";
          type ciena-6500-types:INT {
            range "0..9";
          }
          description
            "Signal Fail Threshold Level.";
        }
        leaf act-avail-ts {
          yang:get-supported "true";
          type string {
            length "1..320";
          }
          description
            "Actual available TS supported by the TRANSMODE.";
        }
        leaf rx-mon {
          yang:get-supported "true";
          type ciena-6500-enums:BOOL_YES_NO_defaultNO;
          description
            "Indicate if the signal is monitored in the Rx direction for alarms and PMs and OMs.";
        }
        leaf rx-term {
          yang:get-supported "true";
          type ciena-6500-enums:BOOL_YES_NO_defaultNO;
          description
            "Indicate if the signal is terminated in the Rx direction or not.";
        }
        leaf tx-mon {
          yang:get-supported "true";
          type ciena-6500-enums:BOOL_YES_NO_defaultNO;
          description
            "Indicate if the signal is monitored in the Tx direction for alarms and PMs and OMs.";
        }
        leaf tx-term {
          yang:get-supported "true";
          type ciena-6500-enums:BOOL_YES_NO_defaultNO;
          description
            "Indicate if the signal is terminated in the Tx direction for alarms and PMs and OMs.";
        }
        leaf degm-intv {
          yang:get-supported "true";
          type ciena-6500-types:INT {
            range "2..10";
          }
          description
            "Consecutive bad intervals required to declare signal degrade";
        }
        leaf degthr-percentage {
          yang:get-supported "true";
          type ciena-6500-types:INT {
            range "1..1000";
          }
          description
            "Percentage of errored blocks required to declare an interval bad";
        }
        leaf-list oductp-rxcondtrig {
          yang:get-supported "true";
          type ciena-6500-enums:rxCondTrig;
          description
            "Determines if Plug Fail/Card Fail and xTTP Port OOS trigger on-ramp conditioning";
        }
        leaf-list caid {
          yang:get-supported "true";
          type ciena-6500-types:aid;
          description
            "Specify the list of M2M PTP AIDs those are required for Mate to Mate Interconnection. Format: M2MPTP1&M2MPTP2&...";
        }
        leaf num-flexts {
          yang:get-supported "true";
          type ciena-6500-types:INT {
            range "1..320";
          }
          description
            "Used to identify the number of flex tributaries comprising this CTP.(Param is applicable only on T-Series shelf.)";
        }
        leaf pst {
          yang:get-supported "true";
          type ciena-6500-enums:PSTfac_RTRV;
          description
            "Identify the primary State";
        }
        leaf-list sst {
          yang:get-supported "true";
          type ciena-6500-enums:SSTfac;
          description
            "Secondary State";
        }
      }
    }
  }

  rpc port-delete-oductp {
    description
      "Delete an ODUCTP Facility";
    yang:handler "tl1";
    input {
      leaf oductp {
        mandatory true;
        description
          "AID in format ODUCTP-shelf-slot-port-rt1Ptp1, ODUCTP-shelf-slot-port-rt1Ptp1-rt2Ptp2, ODUCTP-shelf-slot-port-rt1Ptp1-rt2Ptp2-rt3Ptp3, ODUCTP-shelf-slot-port-rt1Ptp1-rt2Ptp2-rt3Ptp3-rt4Ptp4, ODUCTP-shelf-slot-portSsubport-rt1Ptp1, ODUCTP-shelf-slot-portSsubport-rt1Ptp1-rt2Ptp2, ODUCTP-shelf-slotSsubslot-portSsubport-rt1Ptp1, ODUCTP-shelf-slotSsubslot-portSsubport-rt1Ptp1-rt2Ptp2, ODUCTP-shelf-slotSsubslot-port-rt1Ptp1, ODUCTP-shelf-slotSsubslot-port-rt1Ptp1-rt2Ptp2, ODUCTP-shelf-slotSsubslot-port-rt1Ptp1-rt2Ptp2-rt3Ptp3, ODUCTP-shelf-slot-portPsubport-rt1Ptp1, ODUCTP-shelf-slotSsubslot-port-rt1Ptp1-rt2Ptp2-rt3Ptp3-rt4Ptp4, ODUCTP-shelf-slot-portPsubport-rt1Ptp1-rt2Ptp2, ODUCTP-shelf-slot-portPsubport-rt1Ptp1-rt2Ptp2-rt3Ptp3";
        type ciena-6500-types:aid;
      }
      leaf parent {
        yang:delete-supported "true";
        type enumeration {
          enum NO {
            description
              "immediate ODUTTP parent facility is not to be deleted";
          }
          enum YES {
            description
              "immediate ODUTTP parent facility is to be deleted";
          }
        }
        description
          "Specifies if its immediate ODUTTP parent is to be deleted";
      }
    }
  }

  rpc port-disable-oductp {
    description
      "Switch ODUCTP Facility Out of Service";
    yang:handler "tl1";
    input {
      leaf oductp {
        mandatory true;
        description
          "AID in format ODUCTP-shelf-slot-port-rt1Ptp1, ODUCTP-shelf-slot-port-rt1Ptp1-rt2Ptp2, ODUCTP-shelf-slot-port-rt1Ptp1-rt2Ptp2-rt3Ptp3, ODUCTP-shelf-slot-port-rt1Ptp1-rt2Ptp2-rt3Ptp3-rt4Ptp4, ODUCTP-shelf-slot-portSsubport-rt1Ptp1, ODUCTP-shelf-slot-portSsubport-rt1Ptp1-rt2Ptp2, ODUCTP-shelf-slotSsubslot-portSsubport-rt1Ptp1, ODUCTP-shelf-slotSsubslot-portSsubport-rt1Ptp1-rt2Ptp2, ODUCTP-shelf-slotSsubslot-port-rt1Ptp1, ODUCTP-shelf-slotSsubslot-port-rt1Ptp1-rt2Ptp2, ODUCTP-shelf-slotSsubslot-port-rt1Ptp1-rt2Ptp2-rt3Ptp3, ODUCTP-shelf-slot-portPsubport-rt1Ptp1, ODUCTP-shelf-slotSsubslot-port-rt1Ptp1-rt2Ptp2-rt3Ptp3-rt4Ptp4, ODUCTP-shelf-slot-portPsubport-rt1Ptp1-rt2Ptp2, ODUCTP-shelf-slot-portPsubport-rt1Ptp1-rt2Ptp2-rt3Ptp3";
        type ciena-6500-types:aid;
      }
      leaf parent {
        type enumeration {
          enum NO {
            description
              "immediate ODUTTP parent facility is not to be removed from service";
          }
          enum YES {
            description
              "immediate ODUTTP parent facility is to be removed from service";
          }
        }
        default "NO";
        description
          "Specifies if its immediate ODUTTP parent facility is to be removed from service";
      }
      leaf sst {
        type ciena-6500-enums:RMVSSTMT;
        description
          "Remove facility from Maintenance State";
      }
    }
  }

  rpc port-enable-oductp {
    description
      "Switch ODUTTP Facility In Service";
    yang:handler "tl1";
    input {
      leaf oductp {
        mandatory true;
        description
          "AID in format ODUCTP-shelf-slot-port-rt1Ptp1, ODUCTP-shelf-slot-port-rt1Ptp1-rt2Ptp2, ODUCTP-shelf-slot-port-rt1Ptp1-rt2Ptp2-rt3Ptp3, ODUCTP-shelf-slot-port-rt1Ptp1-rt2Ptp2-rt3Ptp3-rt4Ptp4, ODUCTP-shelf-slot-portSsubport-rt1Ptp1, ODUCTP-shelf-slot-portSsubport-rt1Ptp1-rt2Ptp2, ODUCTP-shelf-slotSsubslot-portSsubport-rt1Ptp1, ODUCTP-shelf-slotSsubslot-portSsubport-rt1Ptp1-rt2Ptp2, ODUCTP-shelf-slotSsubslot-port-rt1Ptp1, ODUCTP-shelf-slotSsubslot-port-rt1Ptp1-rt2Ptp2, ODUCTP-shelf-slotSsubslot-port-rt1Ptp1-rt2Ptp2-rt3Ptp3, ODUCTP-shelf-slot-portPsubport-rt1Ptp1, ODUCTP-shelf-slotSsubslot-port-rt1Ptp1-rt2Ptp2-rt3Ptp3-rt4Ptp4, ODUCTP-shelf-slot-portPsubport-rt1Ptp1-rt2Ptp2, ODUCTP-shelf-slot-portPsubport-rt1Ptp1-rt2Ptp2-rt3Ptp3";
        type ciena-6500-types:aid;
      }
    }
  }

  rpc port-operate-loopback-oductp {
    description
      "Operate loopback on specified facility.";
    yang:handler "tl1";
    input {
      leaf oductp {
        mandatory true;
        description
          "AID in format ODUCTP-shelf-slot-port-rt1Ptp1, ODUCTP-shelf-slot-port-rt1Ptp1-rt2Ptp2, ODUCTP-shelf-slot-port-rt1Ptp1-rt2Ptp2-rt3Ptp3, ODUCTP-shelf-slot-port-rt1Ptp1-rt2Ptp2-rt3Ptp3-rt4Ptp4, ODUCTP-shelf-slot-portSsubport-rt1Ptp1, ODUCTP-shelf-slot-portPsubport-rt1Ptp1-rt2Ptp2, ODUCTP-shelf-slot-portPsubport-rt1Ptp1";
        type ciena-6500-types:aid;
      }
      leaf loopback-type {
        type enumeration {
          enum FACILITY {
            description
              "Signal looped toward the equipment";
          }
          enum TERMINAL {
            description
              "Signal looped away from the equipment";
          }
        }
        description
          "Loopback Type";
      }
    }
  }

  rpc port-release-loopback-oductp {
    description
      "Release loopback on specified facility.";
    yang:handler "tl1";
    input {
      leaf oductp {
        mandatory true;
        description
          "AID in format ODUCTP-shelf-slot-port-rt1Ptp1, ODUCTP-shelf-slot-port-rt1Ptp1-rt2Ptp2, ODUCTP-shelf-slot-port-rt1Ptp1-rt2Ptp2-rt3Ptp3, ODUCTP-shelf-slot-port-rt1Ptp1-rt2Ptp2-rt3Ptp3-rt4Ptp4, ODUCTP-shelf-slot-portSsubport-rt1Ptp1, ODUCTP-shelf-slot-portPsubport-rt1Ptp1-rt2Ptp2, ODUCTP-shelf-slot-portPsubport-rt1Ptp1";
        type ciena-6500-types:aid;
      }
    }
  }

  rpc port-show-loopback-oductp {
    description
      "Retrieve loopback settings.";
    yang:handler "tl1";
    input {
      leaf oductp {
        mandatory true;
        description
          "AID in format ODUCTP-shelf-slot-port-rt1Ptp1, ODUCTP-shelf-slot-port-rt1Ptp1-rt2Ptp2, ODUCTP-shelf-slot-port-rt1Ptp1-rt2Ptp2-rt3Ptp3, ODUCTP-shelf-slot-port-rt1Ptp1-rt2Ptp2-rt3Ptp3-rt4Ptp4, ODUCTP-shelf-slot-portSsubport-rt1Ptp1, ODUCTP-shelf-slot-portPsubport-rt1Ptp1-rt2Ptp2, ODUCTP-shelf-slot-portPsubport-rt1Ptp1";
        type ciena-6500-types:aid;
      }
    }
    output {
      list output {
        leaf oductp {
          yang:get-supported "true";
          type ciena-6500-types:IDENT;
          description
            "aid";
        }
        leaf loopback-type {
          yang:get-supported "true";
          type enumeration {
            enum FACILITY {
              description
                "Signal looped toward the equipment";
            }
            enum TERMINAL {
              description
                "Signal looped away from the equipment";
            }
          }
          description
            "Loopback Type";
        }
      }
    }
  }

  rpc port-show-tcm {
    description
      "Retrieve the TCM facility parameters";
    yang:handler "tl1";
    input {
      leaf tcm {
        mandatory true;
        description
          "AID in format TCMTTP-shelf-slot-port-rt1Ptp1Ttcm, TCMTTP-shelf-slot-port-rt1Ptp1-rt2Ptp2Ttcm, TCMTTP-shelf-slot-port-rt1Ptp1-rt2Ptp2-rt3Ptp3Ttcm, TCMTTP-shelf-slot-port-rt1Ptp1-rt2Ptp2-rt3Ptp3-rt4Ptp4Ttcm, TCMTTP-shelf-slot-portSsubport-rt1Ptp1Ttcm, TCMTTP-shelf-slot-portSsubport-rt1Ptp1-rt2Ptp2Ttcm, TCMTTP-shelf-slotSsubslot-port-rt1Ptp1-rt2Ptp2Ttcm, TCMTTP-shelf-slot-portPsubport-rt1Ptp1Ttcm, TCMTTP-shelf-slotSsubslot-portSsubport-rt1Ptp1Ttcm, TCMTTP-shelf-slotSsubslot-portSsubport-rt1Ptp1-rt2Ptp2Ttcm, TCMTTP-shelf-slotSsubslot-port-rt1Ptp1Ttcm, TCMTTP-shelf-slotSsubslot-port-rt1Ptp1-rt2Ptp2-rt3Ptp3Ttcm, TCMTTP-shelf-slotSsubslot-port-rt1Ptp1-rt2Ptp2-rt3Ptp3-rt4Ptp4Ttcm, TCMTTP-shelf-slot-portPsubport-ALL, TCMTTP-shelf-slot-port-ALL, TCMTTP-shelf-slot-port-rt1Ptp1-rt2Ptp2-rt3Ptp3-rt4Ptp4-ALL, TCMTTP-shelf-slot-port-rt1Ptp1-rt2Ptp2-rt3Ptp3-ALL, TCMTTP-shelf-slot-port-rt1Ptp1-rt2Ptp2-ALL, TCMTTP-shelf-slot-port-rt1Ptp1-ALL, TCMTTP-shelf-slot-ALL, TCMTTP-shelf-ALL, TCMTTP-shelf-slot-portSsubport-ALL, TCMCTP-shelf-slot-port-rt1Ptp1Ttcm, TCMCTP-shelf-slot-port-rt1Ptp1-rt2Ptp2Ttcm, TCMCTP-shelf-slot-port-rt1Ptp1-rt2Ptp2-rt3Ptp3Ttcm, TCMCTP-shelf-slot-port-rt1Ptp1-rt2Ptp2-rt3Ptp3-rt4Ptp4Ttcm, TCMCTP-shelf-slot-portSsubport-rt1Ptp1Ttcm, TCMCTP-shelf-slot-portPsubport-rt1Ptp1Ttcm, TCMCTP-shelf-slot-portSsubport-rt1Ptp1-rt2Ptp2Ttcm, TCMCTP-shelf-slot-port-ALL, TCMCTP-shelf-slot-port-rt1Ptp1-rt2Ptp2-rt3Ptp3-rt4Ptp4-ALL, TCMCTP-shelf-slot-port-rt1Ptp1-rt2Ptp2-rt3Ptp3-ALL, TCMCTP-shelf-slot-port-rt1Ptp1-rt2Ptp2-ALL, TCMCTP-shelf-slot-port-rt1Ptp1-ALL, TCMCTP-shelf-slot-ALL, TCMCTP-shelf-ALL, TCMCTP-shelf-slot-portSsubport-ALL, ALL";
        type ciena-6500-types:aid;
      }
      leaf stats-info {
        yang:get-supported "true";
        type ciena-6500-enums:StatsInfoDefNo;
        description
          "Specify if Dynamic Status Information is to be included in the response.";
      }
    }
    output {
      list output {
        leaf tcm {
          yang:get-supported "true";
          type ciena-6500-types:IDENT;
          description
            "aid";
        }
        leaf label {
          yang:get-supported "true";
          type string {
            length "0..64";
          }
          description
            "User specified Label";
        }
        leaf tcm-mode {
          yang:get-supported "true";
          type ciena-6500-enums:tcmMode;
          description
            "Identifies the mode of the TCM. ";
        }
        leaf tx-sapi {
          yang:get-supported "true";
          type string {
            length "0..15";
          }
          description
            "The Source Access Point Identifier (SAPI), provisioned by the managing system at the termination source, to be placed in the Trail Trace Identifier (TTI) overhead position of the source of a trail.";
        }
        leaf tx-dapi {
          yang:get-supported "true";
          type string {
            length "0..15";
          }
          description
            "The Destination Access Point Identifier (DAPI), provisioned by the managing system at the termination source, to be placed in the Trail Trace Identifier (TTI) overhead position of the source of a trail.";
        }
        leaf tx-oper {
          yang:get-supported "true";
          type string {
            length "0..32";
          }
          description
            "The operator specific part of the Trail Trace Identifier (TTI) information, provisioned by the managing system at the termination source, to be placed in the TTI overhead position of the source of a trail.";
        }
        leaf ex-sapi {
          yang:get-supported "true";
          type string {
            length "0..15";
          }
          description
            "The expected Source Access Point Identifier (SAPI), provisioned by the managing system, to be compared with the received SAPI at the overhead position of the sink for the purpose of checking the integrity of connectivity. ";
        }
        leaf ex-dapi {
          yang:get-supported "true";
          type string {
            length "0..15";
          }
          description
            "The expected Destination Access Point Identifier (DAPI), provisioned by the managing system, to be compared with the received DAPI at the overhead position of the sink for the purpose of checking the integrity of connectivity. ";
        }
        leaf ex-oper {
          yang:get-supported "true";
          type string {
            length "0..32";
          }
          description
            "The expected operator specific part of the Trail Trace Identifier (TTI) information, provisioned by the managing system at the termination source, to be placed in the TTI overhead position of the source of a trail.";
        }
        leaf rx-sapi {
          yang:get-supported "true";
          type string {
            length "0..15";
          }
          description
            "The Source Access Point Identifier (SAPI) recovered from the Trail Trace Identifier (TTI) overhead position at the sink of a trail.";
        }
        leaf rx-dapi {
          yang:get-supported "true";
          type string {
            length "0..15";
          }
          description
            "The Destination Access Point Identifier (DAPI) recovered from the Trail Trace Identifier (TTI) overhead position at the sink of a trail.";
        }
        leaf rx-oper {
          yang:get-supported "true";
          type string {
            length "0..32";
          }
          description
            "The operator specific part of the Trail Trace Identifier (TTI) information, recovered from the TTI overhead position at the sink of a trail.";
        }
        leaf tf-mode {
          yang:get-supported "true";
          type ciena-6500-enums:otntfMode;
          description
            "Trace Fail Mode";
        }
        leaf tim-enable {
          yang:get-supported "true";
          type enumeration {
            enum TIM_SAPI_ONLY {
              description
                "Only checks for SAPI mismatch";
            }
            enum TIM_DAPI_ONLY {
              description
                "Only checks for DAPI mismatch";
            }
            enum TIM_SAPI_DAPI {
              description
                "Checks for SAPI and DAPI mismatch";
            }
          }
          description
            "The Trail Trace Identifier Mismatch (TIM) controls checking for Trace Identifier Mismatch fault detection. ";
        }
        leaf dm-count {
          yang:get-supported "true";
          type ciena-6500-types:STRING;
          description
            "Value of delay measurement in micro seconds.";
        }
        leaf owner {
          yang:get-supported "true";
          type ciena-6500-enums:Owner;
          description
            "Specifies who created this facility.";
        }
        leaf supported-term-pt {
          yang:get-supported "true";
          type ciena-6500-types:aid;
          description
            "The supporting Termination Point.";
        }
        leaf dm-enable {
          yang:get-supported "true";
          type ciena-6500-enums:BOOL_YES_NO;
          description
            "Specify if delay measurement is enable.";
        }
        leaf sd-th {
          default "9";
          yang:get-supported "true";
          type ciena-6500-types:INT {
            range "5..9";
          }
          description
            "Signal degrade threshold value";
        }
        leaf ains-time-left {
          yang:get-supported "true";
          type ciena-6500-types:TIME;
          description
            "The format will be HH-MM for the time left in AINS timeout.";
        }
        leaf rx-mon {
          yang:get-supported "true";
          type ciena-6500-enums:BOOL_YES_NO_defaultNO;
          description
            "Indicate if the signal is monitored in the Rx direction for alarms and PMs and OMs.";
        }
        leaf rx-term {
          yang:get-supported "true";
          type ciena-6500-enums:BOOL_YES_NO_defaultNO;
          description
            "Indicate if the signal is terminated in the Rx direction or not.";
        }
        leaf tx-mon {
          yang:get-supported "true";
          type ciena-6500-enums:BOOL_YES_NO_defaultNO;
          description
            "Indicate if the signal is monitored in the Tx direction for alarms and PMs and OMs.";
        }
        leaf tx-term {
          yang:get-supported "true";
          type ciena-6500-enums:BOOL_YES_NO_defaultNO;
          description
            "Indicate if the signal is terminated in the Tx direction for alarms and PMs and OMs.";
        }
        leaf degm-intv {
          yang:get-supported "true";
          type ciena-6500-types:INT {
            range "2..10";
          }
          description
            "Consecutive bad intervals required to declare signal degrade";
        }
        leaf degthr-percentage {
          yang:get-supported "true";
          type ciena-6500-types:INT {
            range "1..1000";
          }
          description
            "Percentage of errored blocks required to declare an interval bad";
        }
        leaf tcm-condtype {
          yang:get-supported "true";
          type ciena-6500-enums:tcmCondType;
          description
            "TCM/PM layer on-ramp conditioning control";
        }
        leaf rxcondhold-off {
          yang:get-supported "true";
          type ciena-6500-types:INT {
            range "0 | 10 | 20 | 30 | 40 | 50 | 60 | 70 | 80 | 90 | 100 | 200 | 300 | 400 | 500 | 600 | 700 | 800 | 900 | 1000";
          }
          description
            "Signal Conditioning holdoff duration (for Cascaded TPT)";
        }
        leaf-list tcm-rxcondtrig {
          yang:get-supported "true";
          type ciena-6500-enums:rxCondTrig;
          description
            "Determines if Plug Fail/Card Fail and xTTP Port OOS trigger on-ramp conditioning";
        }
        leaf tcm-ltcactmode {
          yang:get-supported "true";
          type ciena-6500-enums:ltcActMode;
          description
            "Control the conditioning and switching sequence action";
        }
        leaf tcm-ltcalmmode {
          yang:get-supported "true";
          type ciena-6500-enums:ltcAlmMode;
          description
            "Enable or disable alarming for LTC fault";
        }
        leaf tcm-txcondtype {
          yang:get-supported "true";
          type ciena-6500-enums:txCondType;
          description
            "Tx Action against Tx faults";
        }
        leaf pst {
          yang:get-supported "true";
          type ciena-6500-enums:PSTfac_RTRV;
          description
            "Identify the primary State";
        }
        leaf-list sst {
          yang:get-supported "true";
          type ciena-6500-enums:SSTfac;
          description
            "Secondary State";
        }
      }
    }
  }

  rpc port-disable-tcm {
    description
      "Switch TCM Facility Out of Service";
    yang:handler "tl1";
    input {
      leaf tcm {
        mandatory true;
        description
          "AID in format TCMTTP-shelf-slot-port-rt1Ptp1Ttcm, TCMTTP-shelf-slot-port-rt1Ptp1-rt2Ptp2Ttcm, TCMTTP-shelf-slot-port-rt1Ptp1-rt2Ptp2-rt3Ptp3Ttcm, TCMTTP-shelf-slot-port-rt1Ptp1-rt2Ptp2-rt3Ptp3-rt4Ptp4Ttcm, TCMTTP-shelf-slot-portSsubport-rt1Ptp1Ttcm, TCMTTP-shelf-slot-portSsubport-rt1Ptp1-rt2Ptp2Ttcm, TCMTTP-shelf-slotSsubslot-port-rt1Ptp1-rt2Ptp2Ttcm, TCMTTP-shelf-slot-portPsubport-rt1Ptp1Ttcm, TCMCTP-shelf-slot-port-rt1Ptp1Ttcm, TCMCTP-shelf-slot-port-rt1Ptp1-rt2Ptp2Ttcm, TCMCTP-shelf-slot-port-rt1Ptp1-rt2Ptp2-rt3Ptp3Ttcm, TCMCTP-shelf-slot-port-rt1Ptp1-rt2Ptp2-rt3Ptp3-rt4Ptp4Ttcm, TCMCTP-shelf-slot-portSsubport-rt1Ptp1Ttcm, TCMCTP-shelf-slot-portPsubport-rt1Ptp1Ttcm, TCMCTP-shelf-slot-portSsubport-rt1Ptp1-rt2Ptp2Ttcm";
        type ciena-6500-types:aid;
      }
      leaf sst {
        type ciena-6500-enums:RMVSSTMT;
        mandatory true;
        description
          "Place the facility in Maintenance State";
      }
    }
  }

  rpc port-enable-tcm {
    description
      "Switch TCM Facility In Service";
    yang:handler "tl1";
    input {
      leaf tcm {
        mandatory true;
        description
          "AID in format TCMTTP-shelf-slot-port-rt1Ptp1Ttcm, TCMTTP-shelf-slot-port-rt1Ptp1-rt2Ptp2Ttcm, TCMTTP-shelf-slot-port-rt1Ptp1-rt2Ptp2-rt3Ptp3Ttcm, TCMTTP-shelf-slot-port-rt1Ptp1-rt2Ptp2-rt3Ptp3-rt4Ptp4Ttcm, TCMTTP-shelf-slot-portSsubport-rt1Ptp1Ttcm, TCMTTP-shelf-slot-portSsubport-rt1Ptp1-rt2Ptp2Ttcm, TCMTTP-shelf-slotSsubslot-port-rt1Ptp1-rt2Ptp2Ttcm, TCMTTP-shelf-slot-portPsubport-rt1Ptp1Ttcm, TCMTTP-shelf-slotSsubslot-portSsubport-rt1Ptp1Ttcm, TCMTTP-shelf-slotSsubslot-portSsubport-rt1Ptp1-rt2Ptp2Ttcm, TCMTTP-shelf-slotSsubslot-port-rt1Ptp1Ttcm, TCMTTP-shelf-slotSsubslot-port-rt1Ptp1-rt2Ptp2-rt3Ptp3Ttcm, TCMTTP-shelf-slotSsubslot-port-rt1Ptp1-rt2Ptp2-rt3Ptp3-rt4Ptp4Ttcm, TCMCTP-shelf-slot-port-rt1Ptp1Ttcm, TCMCTP-shelf-slot-port-rt1Ptp1-rt2Ptp2Ttcm, TCMCTP-shelf-slot-port-rt1Ptp1-rt2Ptp2-rt3Ptp3Ttcm, TCMCTP-shelf-slot-port-rt1Ptp1-rt2Ptp2-rt3Ptp3-rt4Ptp4Ttcm, TCMCTP-shelf-slot-portSsubport-rt1Ptp1Ttcm, TCMCTP-shelf-slot-portPsubport-rt1Ptp1Ttcm, TCMCTP-shelf-slot-portSsubport-rt1Ptp1-rt2Ptp2Ttcm, TCMCTP-shelf-slotSsubslot-portSsubport-rt1Ptp1Ttcm, TCMCTP-shelf-slotSsubslot-portSsubport-rt1Ptp1-rt2Ptp2Ttcm, TCMCTP-shelf-slotSsubslot-port-rt1Ptp1Ttcm, TCMCTP-shelf-slotSsubslot-port-rt1Ptp1-rt2Ptp2Ttcm, TCMCTP-shelf-slotSsubslot-port-rt1Ptp1-rt2Ptp2-rt3Ptp3Ttcm, TCMCTP-shelf-slotSsubslot-port-rt1Ptp1-rt2Ptp2-rt3Ptp3-rt4Ptp4Ttcm";
        type ciena-6500-types:aid;
      }
    }
  }

  rpc port-disable-cbrttp {
    description
      "Switch CBRTTP Facility Out of Service";
    yang:handler "tl1";
    input {
      leaf cbrttp {
        mandatory true;
        description
          "AID in format CBRTTP-shelf-slot-port";
        type ciena-6500-types:aid;
      }
    }
  }

  rpc port-enable-cbrttp {
    description
      "Switch CBRTTP Facility In Service";
    yang:handler "tl1";
    input {
      leaf cbrttp {
        mandatory true;
        description
          "AID in format CBRTTP-shelf-slot-port";
        type ciena-6500-types:aid;
      }
    }
  }

  rpc port-show-cbrttp {
    description
      "Retrieve the CBRTTP facility parameters";
    yang:handler "tl1";
    input {
      leaf cbrttp {
        mandatory true;
        description
          "AID in format CBRTTP-shelf-slot-port, CBRTTP-shelf-slot-ALL, CBRTTP-shelf-ALL, ALL";
        type ciena-6500-types:aid;
      }
      leaf stats-info {
        yang:get-supported "true";
        type ciena-6500-enums:StatsInfoDefYes;
        description
          "Specify if Dynamic Status Information is to be included in the response.";
      }
    }
    output {
      list output {
        leaf cbrttp {
          yang:get-supported "true";
          type ciena-6500-types:IDENT;
          description
            "aid";
        }
        leaf rate {
          yang:get-supported "true";
          type string {
            length "0..11";
          }
          description
            "";
        }
        leaf protocol {
          yang:get-supported "true";
          type ciena-6500-enums:CbrTtpProtocol;
          description
            "";
        }
        leaf an {
          yang:get-supported "true";
          type ciena-6500-enums:AUTO_NEGOTIATION;
          description
            "Indicating whether to perform speed Auto-negotiation";
        }
        leaf label {
          yang:get-supported "true";
          type string {
            length "0..64";
          }
          description
            "User specified Label";
        }
        leaf mapping {
          yang:get-supported "true";
          type ciena-6500-enums:CbrMapping;
          description
            "Defines the mapping of this facility and the children that it will have.";
        }
        leaf hold-off {
          default "100";
          yang:get-supported "true";
          type ciena-6500-types:INT {
            range "0 | 10 | 20 | 30 | 40 | 50 | 60 | 70 | 80 | 90 | 100 | 200 | 300 | 400 | 500 | 600 | 700 | 800 | 900 | 1000";
          }
          description
            "Conditioning holdoff time in seconds.";
        }
        leaf fec-frmt {
          yang:get-supported "true";
          type ciena-6500-enums:CbrFECFrmt;
          description
            "FEC Format";
        }
        leaf pre-fec-sf-th-lev {
          default "0.00";
          yang:get-supported "true";
          type decimal64 {
            range "-1.00..1.00";
            fraction-digits 2;
          }
          description
            "Pre-FEC Signal Fail Threshold";
        }
        leaf pre-fec-sd-th-lev {
          default "0.50";
          yang:get-supported "true";
          type decimal64 {
            range "-1.00..2.00";
            fraction-digits 2;
          }
          description
            "Pre-FEC Signal Degrade Threshold";
        }
        leaf cond-type {
          yang:get-supported "true";
          type ciena-6500-enums:CbrTtpCondType;
          description
            "Specifies ethernet specific client conditioning behaviour.";
        }
        leaf supported-term-pt {
          yang:get-supported "true";
          type ciena-6500-types:aid;
          description
            "The supporting Termination Point.";
        }
        leaf pre-fec-sf-th-ber {
          default "0.0";
          yang:get-supported "true";
          type ciena-6500-types:STRING;
          description
            "The corresponding BER for a given Pre-FEC SF Threshold setting in dDQ";
        }
        leaf pre-fec-sd-th-ber {
          default "0.0";
          yang:get-supported "true";
          type ciena-6500-types:STRING;
          description
            "The corresponding BER for a given Pre-FEC SD Threshold setting in dDQ";
        }
        leaf pst {
          yang:get-supported "true";
          type ciena-6500-enums:PSTfac_RTRV;
          description
            "Identify the primary State";
        }
        leaf-list sst {
          yang:get-supported "true";
          type ciena-6500-enums:SSTfac;
          description
            "Secondary State";
        }
      }
    }
  }

  rpc port-show-pdh {
    description
      "Retrieve attributes for PDH Facility";
    yang:handler "tl1";
    input {
      leaf pdh {
        mandatory true;
        description
          "AID in format PDH-shelf-slot-port-rt1Ptp1-rt2Ptp2, PDH-shelf-slot-port-rt1Ptp1-rt2Ptp2-rt3Ptp3, PDH-shelf-slot-port-rt1Ptp1-rt2Ptp2-rt3Ptp3-rt4Ptp4, PDH-shelf-slot-port-rt1Ptp1-rt2Ptp2-rt3Ptp3-rt4Ptp4-rt5Ptp5, PDH-shelf-slotSsubslot-port-rt1Ptp1, PDH-shelf-slotSsubslot-port-rt1Ptp1-rt2Ptp2, PDH-shelf-slotSsubslot-port-rt1Ptp1-rt2Ptp2-rt3Ptp3, PDH-shelf-slotSsubslot-port-rt1Ptp1-rt2Ptp2-rt3Ptp3-rt4Ptp4, PDH-shelf-slot-port-rt1Ptp1, PDH-shelf-slot-ALL, PDH-shelf-slot-port-ALL, PDH-shelf-slotSsubslot-ALL, PDH-shelf-slotSsubslot-port-ALL, PDH-shelf-ALL, ALL";
        type ciena-6500-types:aid;
      }
      leaf stats-info {
        yang:get-supported "true";
        type ciena-6500-enums:StatsInfoDefNo;
        description
          "Specify if Dynamic Status Information is to be included in the response.";
      }
    }
    output {
      list output {
        leaf pdh {
          yang:get-supported "true";
          type ciena-6500-types:IDENT;
          description
            "aid";
        }
        leaf rate {
          yang:get-supported "true";
          type ciena-6500-enums:PtsTtpPdhRate;
          description
            "Rate";
        }
        leaf far-end-nte {
          yang:get-supported "true";
          type ciena-6500-enums:DS1_NTE;
          description
            "Far End NE Type";
        }
        leaf fault-loc-mode {
          yang:get-supported "true";
          type ciena-6500-enums:DS1_FLMDE;
          description
            "Fault Locate Mode";
        }
        leaf frame-fmt {
          yang:get-supported "true";
          type ciena-6500-enums:frmfmt;
          description
            "Frame Format";
        }
        leaf map {
          yang:get-supported "true";
          type ciena-6500-enums:DS1_MAP;
          description
            "Mapping Type";
        }
        leaf out-mode {
          yang:get-supported "true";
          type ciena-6500-enums:DS1_OMODE;
          description
            "Outgoing Mode";
        }
        leaf label {
          yang:get-supported "true";
          type string {
            length "0..64";
          }
          description
            "User specified Label";
        }
        leaf supported-term-pt {
          yang:get-supported "true";
          type ciena-6500-types:aid;
          description
            "The supporting Termination Point.";
        }
        leaf rx-mon {
          yang:get-supported "true";
          type ciena-6500-enums:BOOL_YES_NO_defaultNO;
          description
            "Indicate if the signal is monitored in the Rx direction for alarms and PMs and OMs.";
        }
        leaf rx-term {
          yang:get-supported "true";
          type ciena-6500-enums:BOOL_YES_NO_defaultNO;
          description
            "Indicate if the signal is terminated in the Rx direction or not.";
        }
        leaf tx-mon {
          yang:get-supported "true";
          type ciena-6500-enums:BOOL_YES_NO_defaultNO;
          description
            "Indicate if the signal is monitored in the Tx direction for alarms and PMs and OMs.";
        }
        leaf tx-term {
          yang:get-supported "true";
          type ciena-6500-enums:BOOL_YES_NO_defaultNO;
          description
            "Indicate if the signal is terminated in the Tx direction for alarms and PMs and OMs.";
        }
        leaf ais_rpt {
          yang:get-supported "true";
          type ciena-6500-enums:BOOL_ON_OFF_defaultOFF;
          description
            "AIS alarm reporting control. Indicates if the facility AIS alarm reporting is On or Off. The value of Off will prevent the AIS alarm from being raised. Default value comes from the system parameter AIS Reporting Default.";
        }
        leaf rai_rpt {
          yang:get-supported "true";
          type ciena-6500-enums:BOOL_ON_OFF_defaultOFF;
          description
            "RAI alarm reporting control. Indicates if the facility RAI alarm reporting is On or Off. The value of Off will prevent the RAI alarm from being raised. Default value comes from the system parameter RFI RAI Reporting Default.";
        }
        leaf summary-contrib {
          yang:get-supported "true";
          type ciena-6500-enums:BOOL_ON_OFF_defaultON;
          description
            "Controls if the facility contributes to summary alarm or summary event.";
        }
        leaf usage {
          yang:get-supported "true";
          type ciena-6500-enums:ptsPDHUsage;
          description
            "Indicate if this PATH can be cross-connected or what child facility can be created.";
        }
        leaf pst {
          yang:get-supported "true";
          type ciena-6500-enums:PSTfac_RTRV;
          description
            "Identify the primary State";
        }
        leaf-list sst {
          yang:get-supported "true";
          type ciena-6500-enums:SSTPDH;
          description
            "Secondary State";
        }
      }
    }
  }

  rpc port-enable-pdh {
    description
      "Switch PDH Facility In Service";
    yang:handler "tl1";
    input {
      leaf pdh {
        mandatory true;
        description
          "AID in format PDH-shelf-slot-port-rt1Ptp1-rt2Ptp2, PDH-shelf-slot-port-rt1Ptp1-rt2Ptp2-rt3Ptp3, PDH-shelf-slot-port-rt1Ptp1-rt2Ptp2-rt3Ptp3-rt4Ptp4, PDH-shelf-slot-port-rt1Ptp1-rt2Ptp2-rt3Ptp3-rt4Ptp4-rt5Ptp5, PDH-shelf-slotSsubslot-port-rt1Ptp1, PDH-shelf-slotSsubslot-port-rt1Ptp1-rt2Ptp2, PDH-shelf-slotSsubslot-port-rt1Ptp1-rt2Ptp2-rt3Ptp3, PDH-shelf-slotSsubslot-port-rt1Ptp1-rt2Ptp2-rt3Ptp3-rt4Ptp4, PDH-shelf-slot-port-rt1Ptp1";
        type ciena-6500-types:aid;
      }
    }
  }

  rpc port-disable-pdh {
    description
      "Switch PDH Facility Out of Service";
    yang:handler "tl1";
    input {
      leaf pdh {
        mandatory true;
        description
          "AID in format PDH-shelf-slot-port-rt1Ptp1-rt2Ptp2, PDH-shelf-slot-port-rt1Ptp1-rt2Ptp2-rt3Ptp3, PDH-shelf-slot-port-rt1Ptp1-rt2Ptp2-rt3Ptp3-rt4Ptp4, PDH-shelf-slot-port-rt1Ptp1-rt2Ptp2-rt3Ptp3-rt4Ptp4-rt5Ptp5, PDH-shelf-slotSsubslot-port-rt1Ptp1, PDH-shelf-slotSsubslot-port-rt1Ptp1-rt2Ptp2, PDH-shelf-slotSsubslot-port-rt1Ptp1-rt2Ptp2-rt3Ptp3, PDH-shelf-slotSsubslot-port-rt1Ptp1-rt2Ptp2-rt3Ptp3-rt4Ptp4, PDH-shelf-slot-port-rt1Ptp1";
        type ciena-6500-types:aid;
      }
      leaf sst {
        type ciena-6500-enums:RMVSSTMT;
        description
          "Remove facility from Maintenance State";
      }
    }
  }

  rpc port-operate-loopback-pdh {
    description
      "Operate loopback on specified facility.";
    yang:handler "tl1";
    input {
      leaf pdh {
        mandatory true;
        description
          "AID in format PDH-shelf-slot-port-rt1Ptp1-rt2Ptp2, PDH-shelf-slot-port-rt1Ptp1-rt2Ptp2-rt3Ptp3, PDH-shelf-slot-port-rt1Ptp1-rt2Ptp2-rt3Ptp3-rt4Ptp4, PDH-shelf-slot-port-rt1Ptp1-rt2Ptp2-rt3Ptp3-rt4Ptp4-rt5Ptp5, PDH-shelf-slotSsubslot-port-rt1Ptp1, PDH-shelf-slotSsubslot-port-rt1Ptp1-rt2Ptp2, PDH-shelf-slotSsubslot-port-rt1Ptp1-rt2Ptp2-rt3Ptp3, PDH-shelf-slotSsubslot-port-rt1Ptp1-rt2Ptp2-rt3Ptp3-rt4Ptp4, PDH-shelf-slot-port-rt1Ptp1";
        type ciena-6500-types:aid;
      }
      leaf loopback-locn {
        type ciena-6500-enums:LpbkLocn;
        description
          "Loopback Location";
      }
      leaf loopback-type {
        type ciena-6500-enums:PDH_lpbk;
        description
          "Loopback Type";
      }
    }
  }

  rpc port-release-loopback-pdh {
    description
      "Release loopback on specified facility.";
    yang:handler "tl1";
    input {
      leaf pdh {
        mandatory true;
        description
          "AID in format PDH-shelf-slot-port-rt1Ptp1-rt2Ptp2, PDH-shelf-slot-port-rt1Ptp1-rt2Ptp2-rt3Ptp3, PDH-shelf-slot-port-rt1Ptp1-rt2Ptp2-rt3Ptp3-rt4Ptp4, PDH-shelf-slot-port-rt1Ptp1-rt2Ptp2-rt3Ptp3-rt4Ptp4-rt5Ptp5, PDH-shelf-slotSsubslot-port-rt1Ptp1, PDH-shelf-slotSsubslot-port-rt1Ptp1-rt2Ptp2, PDH-shelf-slotSsubslot-port-rt1Ptp1-rt2Ptp2-rt3Ptp3, PDH-shelf-slotSsubslot-port-rt1Ptp1-rt2Ptp2-rt3Ptp3-rt4Ptp4, PDH-shelf-slot-port-rt1Ptp1";
        type ciena-6500-types:aid;
      }
    }
  }

  rpc port-show-loopback-pdh {
    description
      "Retrieve loopback settings.";
    yang:handler "tl1";
    input {
      leaf pdh {
        mandatory true;
        description
          "AID in format PDH-shelf-slot-port-rt1Ptp1-rt2Ptp2, PDH-shelf-slot-port-rt1Ptp1-rt2Ptp2-rt3Ptp3, PDH-shelf-slot-port-rt1Ptp1-rt2Ptp2-rt3Ptp3-rt4Ptp4, PDH-shelf-slot-port-rt1Ptp1-rt2Ptp2-rt3Ptp3-rt4Ptp4-rt5Ptp5, PDH-shelf-slotSsubslot-port-rt1Ptp1, PDH-shelf-slotSsubslot-port-rt1Ptp1-rt2Ptp2, PDH-shelf-slotSsubslot-port-rt1Ptp1-rt2Ptp2-rt3Ptp3, PDH-shelf-slotSsubslot-port-rt1Ptp1-rt2Ptp2-rt3Ptp3-rt4Ptp4, PDH-shelf-slot-port-rt1Ptp1, PDH-shelf-slot-ALL, PDH-shelf-slot-port-ALL, PDH-shelf-slotSsubslot-ALL, PDH-shelf-slotSsubslot-port-ALL, PDH-shelf-ALL";
        type ciena-6500-types:aid;
      }
    }
    output {
      list output {
        leaf pdh {
          yang:get-supported "true";
          type ciena-6500-types:IDENT;
          description
            "aid";
        }
        leaf loopback-locn {
          yang:get-supported "true";
          type ciena-6500-enums:LpbkLocn;
          description
            "Loopback Location";
        }
        leaf loopback-type {
          yang:get-supported "true";
          type ciena-6500-enums:PDH_lpbk;
          description
            "Loopback Type";
        }
        leaf lpbk-remlpbk {
          yang:get-supported "true";
          type ciena-6500-enums:RemLpbk;
          description
            "Remote loopback is allowed or inhibited";
        }
      }
    }
  }

  rpc port-alw-loopback-pdh {
    description
      "Allow remote loopback on a PDH facility.";
    yang:handler "tl1";
    input {
      leaf pdh {
        mandatory true;
        description
          "AID in format PDH-shelf-slot-port-rt1Ptp1-rt2Ptp2, PDH-shelf-slot-port-rt1Ptp1-rt2Ptp2-rt3Ptp3, PDH-shelf-slot-port-rt1Ptp1-rt2Ptp2-rt3Ptp3-rt4Ptp4, PDH-shelf-slot-port-rt1Ptp1-rt2Ptp2-rt3Ptp3-rt4Ptp4-rt5Ptp5, PDH-shelf-slotSsubslot-port-rt1Ptp1, PDH-shelf-slotSsubslot-port-rt1Ptp1-rt2Ptp2, PDH-shelf-slotSsubslot-port-rt1Ptp1-rt2Ptp2-rt3Ptp3, PDH-shelf-slotSsubslot-port-rt1Ptp1-rt2Ptp2-rt3Ptp3-rt4Ptp4, PDH-shelf-slot-port-rt1Ptp1";
        type ciena-6500-types:aid;
      }
    }
  }

  rpc port-inh-loopback-pdh {
    description
      "Inhibit remote loopback on a PDH facility.";
    yang:handler "tl1";
    input {
      leaf pdh {
        mandatory true;
        description
          "AID in format PDH-shelf-slot-port-rt1Ptp1-rt2Ptp2, PDH-shelf-slot-port-rt1Ptp1-rt2Ptp2-rt3Ptp3, PDH-shelf-slot-port-rt1Ptp1-rt2Ptp2-rt3Ptp3-rt4Ptp4, PDH-shelf-slot-port-rt1Ptp1-rt2Ptp2-rt3Ptp3-rt4Ptp4-rt5Ptp5, PDH-shelf-slotSsubslot-port-rt1Ptp1, PDH-shelf-slotSsubslot-port-rt1Ptp1-rt2Ptp2, PDH-shelf-slotSsubslot-port-rt1Ptp1-rt2Ptp2-rt3Ptp3, PDH-shelf-slotSsubslot-port-rt1Ptp1-rt2Ptp2-rt3Ptp3-rt4Ptp4, PDH-shelf-slot-port-rt1Ptp1";
        type ciena-6500-types:aid;
      }
    }
  }

  rpc port-show-path {
    description
      "Retrieve attributes for PATH Facility";
    yang:handler "tl1";
    input {
      leaf path {
        mandatory true;
        description
          "AID in format PATH-shelf-slot-port-rt1Ptp1, PATH-shelf-slot-port-rt1Ptp1-rt2Ptp2, PATH-shelf-slot-port-rt1Ptp1-rt2Ptp2-rt3Ptp3, PATH-shelf-slot-port-rt1Ptp1-rt2Ptp2-rt3Ptp3-rt4Ptp4, PATH-shelf-slotSsubslot-port-rt1Ptp1, PATH-shelf-slotSsubslot-port-rt1Ptp1-rt2Ptp2-rt3Ptp3, PATH-shelf-slot-ALL, PATH-shelf-slot-port-ALL, PATH-shelf-slotSsubslot-ALL, PATH-shelf-slotSsubslot-port-ALL, PATH-shelf-ALL, ALL";
        type ciena-6500-types:aid;
      }
      leaf stats-info {
        yang:get-supported "true";
        type ciena-6500-enums:StatsInfoDefNo;
        description
          "Specify if Dynamic Status Information is to be included in the response.";
      }
    }
    output {
      list output {
        leaf path {
          yang:get-supported "true";
          type ciena-6500-types:IDENT;
          description
            "aid";
        }
        leaf exp-sig-label {
          yang:get-supported "true";
          type ciena-6500-types:INT {
            range "0..4";
          }
          description
            "Expected signal label";
        }
        leaf in-sig-label {
          yang:get-supported "true";
          type union {
            type enumeration {
              enum UNKNOWN;
            }
            type ciena-6500-types:INT {
              range "1..4";
            }
          }
          description
            "Incoming signal label";
        }
        leaf out-sig-label {
          yang:get-supported "true";
          type ciena-6500-types:INT {
            range "0..4";
          }
          description
            "Outgoing signal label";
        }
        leaf exp-path-trace {
          yang:get-supported "true";
          type string {
            length "1..62";
          }
          description
            "Expected path trace: 15 characters when TRCFORMAT is 16BYTE, 62 characters when TRCFORMAT is 64BYTE";
        }
        leaf in-path-trace {
          yang:get-supported "true";
          type string {
            length "1..62";
          }
          description
            "Incoming path trace: 15 characters when TRCFORMAT is 16BYTE, 62 characters when TRCFORMAT is 64BYTE";
        }
        leaf out-path-trace {
          yang:get-supported "true";
          type string {
            length "1..62";
          }
          description
            "Outgoing path trace: 15 characters when TRCFORMAT is 16BYTE, 62 characters when TRCFORMAT is 64BYTE";
        }
        leaf trc-format {
          yang:get-supported "true";
          type ciena-6500-enums:trcFormat;
          description
            "TRC Format";
        }
        leaf tf-mode {
          yang:get-supported "true";
          type ciena-6500-enums:pathtfMode;
          description
            "Trace Fail Mode";
        }
        leaf label {
          yang:get-supported "true";
          type string {
            length "0..64";
          }
          description
            "User specified Label";
        }
        leaf rate {
          yang:get-supported "true";
          type ciena-6500-enums:PtsTtpPathRate;
          description
            "Rate";
        }
        leaf supported-term-pt {
          yang:get-supported "true";
          type ciena-6500-types:aid;
          description
            "The supporting Termination Point.";
        }
        leaf rx-mon {
          yang:get-supported "true";
          type ciena-6500-enums:BOOL_YES_NO_defaultNO;
          description
            "Indicate if the signal is monitored in the Rx direction for alarms and PMs and OMs.";
        }
        leaf rx-term {
          yang:get-supported "true";
          type ciena-6500-enums:BOOL_YES_NO_defaultNO;
          description
            "Indicate if the signal is terminated in the Rx direction or not.";
        }
        leaf tx-mon {
          yang:get-supported "true";
          type ciena-6500-enums:BOOL_YES_NO_defaultNO;
          description
            "Indicate if the signal is monitored in the Tx direction for alarms and PMs and OMs.";
        }
        leaf tx-term {
          yang:get-supported "true";
          type ciena-6500-enums:BOOL_YES_NO_defaultNO;
          description
            "Indicate if the signal is terminated in the Tx direction for alarms and PMs and OMs.";
        }
        leaf ais_rpt {
          yang:get-supported "true";
          type ciena-6500-enums:BOOL_ON_OFF_defaultOFF;
          description
            "AIS alarm reporting control. Indicates if the facility AIS alarm reporting is On or Off. The value of Off will prevent the AIS alarm from being raised. Default value comes from the system parameter AIS Reporting Default.";
        }
        leaf rfi_rpt {
          yang:get-supported "true";
          type ciena-6500-enums:BOOL_ON_OFF_defaultOFF;
          description
            "RFI alarm reporting control. Indicates if the facility RFI alarm reporting is On or Off. The value of Off will prevent the RFI alarm from being raised. Default value comes from the system parameter RFI RAI Reporting Default.";
        }
        leaf summary-contrib {
          yang:get-supported "true";
          type ciena-6500-enums:BOOL_ON_OFF_defaultON;
          description
            "Controls if the facility contributes to summary alarm or summary event.";
        }
        leaf usage {
          yang:get-supported "true";
          type ciena-6500-enums:ptsMROUsage;
          description
            "Indicate if this PATH can be cross-connected or what child facility can be created.";
        }
        leaf pst {
          yang:get-supported "true";
          type ciena-6500-enums:PSTfac_RTRV;
          description
            "Identify the primary State";
        }
        leaf-list sst {
          yang:get-supported "true";
          type ciena-6500-enums:SSTPATH;
          description
            "Secondary State";
        }
      }
    }
  }

  rpc port-enable-path {
    description
      "Switch PATH Facility In Service";
    yang:handler "tl1";
    input {
      leaf path {
        mandatory true;
        description
          "AID in format PATH-shelf-slot-port-rt1Ptp1, PATH-shelf-slot-port-rt1Ptp1-rt2Ptp2, PATH-shelf-slot-port-rt1Ptp1-rt2Ptp2-rt3Ptp3, PATH-shelf-slot-port-rt1Ptp1-rt2Ptp2-rt3Ptp3-rt4Ptp4, PATH-shelf-slotSsubslot-port-rt1Ptp1, PATH-shelf-slotSsubslot-port-rt1Ptp1-rt2Ptp2-rt3Ptp3";
        type ciena-6500-types:aid;
      }
    }
  }

  rpc port-disable-path {
    description
      "Switch PATH Facility Out of Service";
    yang:handler "tl1";
    input {
      leaf path {
        mandatory true;
        description
          "AID in format PATH-shelf-slot-port-rt1Ptp1, PATH-shelf-slot-port-rt1Ptp1-rt2Ptp2, PATH-shelf-slot-port-rt1Ptp1-rt2Ptp2-rt3Ptp3, PATH-shelf-slot-port-rt1Ptp1-rt2Ptp2-rt3Ptp3-rt4Ptp4, PATH-shelf-slotSsubslot-port-rt1Ptp1, PATH-shelf-slotSsubslot-port-rt1Ptp1-rt2Ptp2-rt3Ptp3";
        type ciena-6500-types:aid;
      }
      leaf sst {
        type ciena-6500-enums:RMVSSTMT;
        description
          "Remove facility from Maintenance State";
      }
    }
  }

  rpc port-operate-loopback-path {
    description
      "Operate loopback on specified facility.";
    yang:handler "tl1";
    input {
      leaf path {
        mandatory true;
        description
          "AID in format PATH-shelf-slot-port-rt1Ptp1, PATH-shelf-slot-port-rt1Ptp1-rt2Ptp2, PATH-shelf-slot-port-rt1Ptp1-rt2Ptp2-rt3Ptp3, PATH-shelf-slot-port-rt1Ptp1-rt2Ptp2-rt3Ptp3-rt4Ptp4, PATH-shelf-slotSsubslot-port-rt1Ptp1, PATH-shelf-slotSsubslot-port-rt1Ptp1-rt2Ptp2-rt3Ptp3";
        type ciena-6500-types:aid;
      }
      leaf loopback-type {
        type ciena-6500-enums:FLEXLoopBack;
        description
          "Loopback Type";
      }
    }
  }

  rpc port-release-loopback-path {
    description
      "Release loopback on specified facility.";
    yang:handler "tl1";
    input {
      leaf path {
        mandatory true;
        description
          "AID in format PATH-shelf-slot-port-rt1Ptp1, PATH-shelf-slot-port-rt1Ptp1-rt2Ptp2, PATH-shelf-slot-port-rt1Ptp1-rt2Ptp2-rt3Ptp3, PATH-shelf-slot-port-rt1Ptp1-rt2Ptp2-rt3Ptp3-rt4Ptp4, PATH-shelf-slotSsubslot-port-rt1Ptp1, PATH-shelf-slotSsubslot-port-rt1Ptp1-rt2Ptp2-rt3Ptp3";
        type ciena-6500-types:aid;
      }
    }
  }

  rpc port-show-loopback-path {
    description
      "Retrieve loopback settings.";
    yang:handler "tl1";
    input {
      leaf path {
        mandatory true;
        description
          "AID in format PATH-shelf-slot-port-rt1Ptp1, PATH-shelf-slot-port-rt1Ptp1-rt2Ptp2, PATH-shelf-slot-port-rt1Ptp1-rt2Ptp2-rt3Ptp3, PATH-shelf-slot-port-rt1Ptp1-rt2Ptp2-rt3Ptp3-rt4Ptp4, PATH-shelf-slotSsubslot-port-rt1Ptp1, PATH-shelf-slotSsubslot-port-rt1Ptp1-rt2Ptp2-rt3Ptp3, PATH-shelf-slot-ALL, PATH-shelf-slot-port-ALL, PATH-shelf-slotSsubslot-ALL, PATH-shelf-slotSsubslot-port-ALL, PATH-shelf-ALL";
        type ciena-6500-types:aid;
      }
    }
    output {
      list output {
        leaf path {
          yang:get-supported "true";
          type ciena-6500-types:IDENT;
          description
            "aid";
        }
        leaf loopback-type {
          yang:get-supported "true";
          type ciena-6500-enums:FLEXLoopBack;
          description
            "Loopback Type";
        }
      }
    }
  }

  rpc port-show-pktiwf {
    description
      "Retrieve attributes for PKTIWF Facility";
    yang:handler "tl1";
    input {
      leaf pktiwf {
        mandatory true;
        description
          "AID in format PKTIWF-shelf-slot-iwfid, PKTIWF-shelf-slotSsubslot-iwfid, PKTIWF-shelf-slot-ALL, PKTIWF-shelf-slotSsubslot-ALL, PKTIWF-shelf-ALL, ALL";
        type ciena-6500-types:aid;
      }
      leaf stats-info {
        yang:get-supported "true";
        type ciena-6500-enums:StatsInfoDefNo;
        description
          "Specify if Dynamic Status Information is to be included in the response.";
      }
    }
    output {
      list output {
        leaf pktiwf {
          yang:get-supported "true";
          type ciena-6500-types:IDENT;
          description
            "aid";
        }
        leaf cas {
          yang:get-supported "true";
          type ciena-6500-enums:BOOL_ON_OFF_defaultOFF;
          description
            "Channel Associated Signaling";
        }
        leaf clk-rec-mode {
          yang:get-supported "true";
          type ciena-6500-enums:clkRecoveryMode;
          description
            "Clock Recovery Mode";
        }
        leaf ds0-map {
          yang:get-supported "true";
          type ciena-6500-types:STRING;
          description
            "DS0MAP";
        }
        leaf in-payload-type {
          default "0";
          yang:get-supported "true";
          type union {
            type enumeration {
              enum UNKNOWN;
            }
            type ciena-6500-types:INT {
              range "0..127";
            }
          }
          description
            "Incoming RTP Header Payload Type from the fabric. 7 bit integer (0..127) with values as described in MEF8 and defined in http://www.iana.org/assignments/rtp-parameters/rtp-parameters.xhtml.";
        }
        leaf in-sync-src {
          default "0";
          yang:get-supported "true";
          type union {
            type enumeration {
              enum UNKNOWN;
            }
            type ciena-6500-types:INT {
              range "0..4294967295";
            }
          }
          description
            "Incoming RTP Header Synchronization Source from the fabric. 32 bit integer.";
        }
        leaf jitter-buffer-depth {
          default "5";
          yang:get-supported "true";
          type ciena-6500-types:INT {
            range "1..32";
          }
          description
            "Jitter Buffer Depth in milliseconds in 1 msec increments.";
        }
        leaf label {
          yang:get-supported "true";
          type string {
            length "0..64";
          }
          description
            "User specified Label";
        }
        leaf mapping {
          yang:get-supported "true";
          type ciena-6500-enums:PktiwfMapping;
          description
            "Packet Mapping";
        }
        leaf out-payload-type {
          default "0";
          yang:get-supported "true";
          type ciena-6500-types:INT {
            range "0..127";
          }
          description
            "Outgoing TX RTP Header Payload Type towards the fabric. 7 bit integer (0..127) with values as described in MEF8 and defined here: http://www.iana.org/assignments/rtp-parameters/rtp-parameters.xhtml";
        }
        leaf out-sync-src {
          default "0";
          yang:get-supported "true";
          type ciena-6500-types:INT {
            range "0..4294967295";
          }
          description
            "Outgoing RTP Header Synchronization Source towards the fabric. 32 bit integer (0..4294967295)";
        }
        leaf ptr-proc-mode {
          yang:get-supported "true";
          type ciena-6500-enums:ptrProcessingMode;
          description
            "Pointer Processing Mode";
        }
        leaf payload-size {
          yang:get-supported "true";
          type ciena-6500-types:INT {
            range "96..4092";
          }
          description
            "Packet Payload Size in bytes";
        }
        leaf rate {
          yang:get-supported "true";
          type ciena-6500-enums:pktiwfRate;
          description
            "Rate of interworking function";
        }
        leaf rtp-header {
          yang:get-supported "true";
          type ciena-6500-enums:BOOL_YES_NO_defaultNO;
          description
            "Indicates whether to include the RTP Header";
        }
        leaf tx-mon {
          yang:get-supported "true";
          type ciena-6500-enums:BOOL_YES_NO_defaultNO;
          description
            "Indicates if signal is monitored in TX direction for alarms and PMs";
        }
        leaf tx-term {
          yang:get-supported "true";
          type ciena-6500-enums:BOOL_YES_NO_defaultYES;
          description
            "Indicates if signal is terminated in TX direction";
        }
        leaf supported-term-pt {
          yang:get-supported "true";
          type ciena-6500-types:aid;
          description
            "Supporting Termination Point";
        }
        leaf summary-contrib {
          yang:get-supported "true";
          type ciena-6500-enums:BOOL_ON_OFF_defaultON;
          description
            "Controls if the facility contributes to summary alarm or summary event.";
        }
        leaf abcd1 {
          yang:get-supported "true";
          type string {
            length "1";
          }
          description
            "Specifies the ABCD1 conditioning code to be used in the signaling bits of a DS0. This attribute is only applicable on cards which have the enhanced DS0 support enabled.";
        }
        leaf abcd1enable {
          yang:get-supported "true";
          type ciena-6500-enums:DISABLE_ENABLE;
          description
            "Indicates if the ABCD1 conditioning codes are enabled or disabled. This attribute is only applicable on cards which have the enhanced DS0 support enabled.";
        }
        leaf abcd2 {
          yang:get-supported "true";
          type string {
            length "1";
          }
          description
            "Specifies the ABCD2 conditioning code to be used in the signaling bits of a DS0. This attribute is only applicable on cards which have the enhanced DS0 support enabled.";
        }
        leaf abcd2enable {
          yang:get-supported "true";
          type ciena-6500-enums:DISABLE_ENABLE;
          description
            "Indicates if the ABCD2 conditioning codes are enabled or disabled. This attribute is only applicable on cards which have the enhanced DS0 support enabled.";
        }
        leaf idlecode {
          yang:get-supported "true";
          type string {
            length "1..2";
          }
          description
            " Idle code. Attribute is only applicable on cards which have the enhanced DS0 support enabled.";
        }
        leaf tap1 {
          yang:get-supported "true";
          type ciena-6500-types:aid;
          description
            "TAP1";
        }
        leaf tap2 {
          yang:get-supported "true";
          type ciena-6500-types:aid;
          description
            "TAP2";
        }
        leaf pst {
          yang:get-supported "true";
          type ciena-6500-enums:PSTfac_RTRV;
          description
            "Identify the primary State";
        }
        leaf-list sst {
          yang:get-supported "true";
          type ciena-6500-enums:SSTPKTIWF;
          description
            "Secondary State";
        }
      }
    }
  }

  rpc port-enable-pktiwf {
    description
      "Switch PKTIWF Facility In Service";
    yang:handler "tl1";
    input {
      leaf pktiwf {
        mandatory true;
        description
          "AID in format PKTIWF-shelf-slot-iwfid, PKTIWF-shelf-slotSsubslot-iwfid";
        type ciena-6500-types:aid;
      }
    }
  }

  rpc port-disable-pktiwf {
    description
      "Switch PKTIWF Facility Out of Service";
    yang:handler "tl1";
    input {
      leaf pktiwf {
        mandatory true;
        description
          "AID in format PKTIWF-shelf-slot-iwfid, PKTIWF-shelf-slotSsubslot-iwfid";
        type ciena-6500-types:aid;
      }
      leaf sst {
        type ciena-6500-enums:RMVSSTMT;
        description
          "Remove facility from Maintenance State";
      }
    }
  }

  rpc port-operate-loopback-cbrttp {
    description
      "Operate loopback on specified facility.";
    yang:handler "tl1";
    input {
      leaf cbrttp {
        mandatory true;
        description
          "AID in format CBRTTP-shelf-slot-port";
        type ciena-6500-types:aid;
      }
      leaf loopback-type {
        type enumeration {
          enum FACILITY {
            description
              "Signal looped toward the equipment";
          }
          enum TERMINAL {
            description
              "Signal looped away from the equipment";
          }
        }
        description
          "Loopback Type";
      }
    }
  }

  rpc port-release-loopback-cbrttp {
    description
      "Release loopback on specified facility.";
    yang:handler "tl1";
    input {
      leaf cbrttp {
        mandatory true;
        description
          "AID in format CBRTTP-shelf-slot-port";
        type ciena-6500-types:aid;
      }
    }
  }

  rpc port-show-loopback-cbrttp {
    description
      "Retrieve loopback settings.";
    yang:handler "tl1";
    input {
      leaf cbrttp {
        mandatory true;
        description
          "AID in format CBRTTP-shelf-slot-port";
        type ciena-6500-types:aid;
      }
    }
    output {
      list output {
        leaf cbrttp {
          yang:get-supported "true";
          type ciena-6500-types:IDENT;
          description
            "aid";
        }
        leaf loopback-type {
          yang:get-supported "true";
          type enumeration {
            enum FACILITY {
              description
                "Signal looped toward the equipment";
            }
            enum TERMINAL {
              description
                "Signal looped away from the equipment";
            }
          }
          description
            "Loopback Type";
        }
      }
    }
  }

  rpc port-disable-flexi {
    description
      "Switch FLEXI Facility Out of Service";
    yang:handler "tl1";
    input {
      leaf flexi {
        mandatory true;
        description
          "AID in format FLEXI-shelf-slot-port-index, FLEXI-shelf-slot-portSsubport-index, FLEXI-shelf-slot-port";
        type ciena-6500-types:aid;
      }
    }
  }

  rpc port-enable-flexi {
    description
      "Switch FLEXI Facility In Service";
    yang:handler "tl1";
    input {
      leaf flexi {
        mandatory true;
        description
          "AID in format FLEXI-shelf-slot-port-index, FLEXI-shelf-slot-portSsubport-index, FLEXI-shelf-slot-port";
        type ciena-6500-types:aid;
      }
    }
  }

  rpc port-show-flexi {
    description
      "Retrieve the FLEXI facility parameters";
    yang:handler "tl1";
    input {
      leaf flexi {
        mandatory true;
        description
          "AID in format FLEXI-shelf-slot-port-index, FLEXI-shelf-slot-portSsubport-index, FLEXI-shelf-slot-port, FLEXI-shelf-slot-ALL, FLEXI-shelf-ALL, ALL";
        type ciena-6500-types:aid;
      }
      leaf stats-info {
        yang:get-supported "true";
        type ciena-6500-enums:StatsInfoDefYes;
        description
          "Specify if Dynamic Status Information is to be included in the response.";
      }
    }
    output {
      list output {
        leaf flexi {
          yang:get-supported "true";
          type ciena-6500-types:IDENT;
          description
            "aid";
        }
        leaf label {
          yang:get-supported "true";
          type string {
            length "0..64";
          }
          description
            "User specified Label";
        }
        leaf flexi-type {
          yang:get-supported "true";
          type ciena-6500-enums:flexIType;
          description
            "Flexi Type";
        }
        leaf tx-gid {
          default "1";
          yang:get-supported "true";
          type ciena-6500-types:INT {
            range "1..1048575";
          }
          description
            "Tx Group ID";
        }
        leaf rx-gid {
          yang:get-supported "true";
          type ciena-6500-types:INT {
            range "1..1048575";
          }
          description
            "Rx Group ID";
        }
        leaf tx-iid {
          yang:get-supported "true";
          type ciena-6500-types:INT {
            range "1..254";
          }
          description
            "Tx Instance ID";
        }
        leaf rx-iid {
          yang:get-supported "true";
          type ciena-6500-types:INT {
            range "1..254";
          }
          description
            "Rx Instance ID";
        }
        leaf p-aid {
          yang:get-supported "true";
          type ciena-6500-types:aid;
          description
            "Specify the Prime FLEXI AID.";
        }
        leaf-list m-aid {
          yang:get-supported "true";
          type ciena-6500-types:aid;
          description
            "Specify the Member FLEXI AID List. Format: Member2&Member3&...";
        }
        leaf tx-flexi-map {
          yang:get-supported "true";
          type ciena-6500-types:STRING;
          description
            "Tx FLEXI Mapping Bitmap";
        }
        leaf rx-flexi-map {
          yang:get-supported "true";
          type ciena-6500-types:STRING;
          description
            "Rx FLEXI Mapping Bitmap";
        }
        leaf role {
          yang:get-supported "true";
          type ciena-6500-enums:flexIRole;
          description
            "Role type in OTUCn-M configuration";
        }
        leaf supported-term-pt {
          yang:get-supported "true";
          type ciena-6500-types:aid;
          description
            "The supporting Termination Point.";
        }
        leaf ains-time-left {
          yang:get-supported "true";
          type ciena-6500-types:TIME;
          description
            "The format will be \"HH-MM\" for the time left in AINS timeout.";
        }
        leaf pst {
          yang:get-supported "true";
          type ciena-6500-enums:PSTfac_RTRV;
          description
            "Identify the primary State";
        }
        leaf-list sst {
          yang:get-supported "true";
          type ciena-6500-enums:SSTfac;
          description
            "Secondary State";
        }
      }
    }
  }

  rpc port-show-odu {
    description
      "Retrieve parameters against the ODU Facility";
    yang:handler "tl1";
    input {
      leaf odun {
        mandatory true;
        description
          "AID in format ODU0-shelf-slot-port-payloadindex, ODU1-shelf-slot-port-payloadindex, ODUFLEX-shelf-slot-port-payloadindex, ODU4-shelf-slot-port-index";
        type ciena-6500-types:aid;
      }
      leaf tti-info {
        yang:get-supported "true";
        type enumeration {
          enum NO {
            description
              "Do not include TTI information in the response";
          }
          enum YES {
            description
              "Include TTI information in the response";
          }
        }
        description
          "Specify if TTI Information is to be included in the response (default is NO).";
      }
      leaf stats-info {
        yang:get-supported "true";
        type enumeration {
          enum NO {
            description
              "Do not include actual RX tribslots in the response";
          }
          enum YES {
            description
              "Include actual RX tribslots in the response";
          }
        }
        description
          "Specify if the actual RX tribslots is to be included in the response (default is NO).";
      }
      leaf odu-flags {
        yang:get-supported "true";
        type enumeration {
          enum NO {
            description
              "Do not include detailed ODU termination and monitoring information in the response";
          }
          enum YES {
            description
              "Include detailed ODU termination and monitoring in the response";
          }
        }
        description
          "Specify if ODU Layer termination and monitoring indicators are to be included in the response (default is NO).";
      }
    }
    output {
      list output {
        leaf odun {
          yang:get-supported "true";
          type ciena-6500-types:IDENT;
          description
            "aid";
        }
        leaf odu-tx-tti {
          yang:get-supported "true";
          type ciena-6500-types:STRING;
          description
            "Transmitted TTI 32B. TTI =ODU Trail Trace Identifier";
        }
        leaf odu-rx-exp-tti {
          yang:get-supported "true";
          type ciena-6500-types:STRING;
          description
            "Expected 32 Characters ODU TTI";
        }
        leaf odu-tx-sapi {
          yang:get-supported "true";
          type ciena-6500-types:STRING;
          description
            "ODU Transmitted SAPI TTI (15 Characters). TTI = Trail Trace Identifier";
        }
        leaf odu-tx-dapi {
          yang:get-supported "true";
          type ciena-6500-types:STRING;
          description
            "ODU Transmitted DAPI TTI (15 Characters). TTI = Trail Trace Identifier";
        }
        leaf odu-ex-sapi {
          yang:get-supported "true";
          type ciena-6500-types:STRING;
          description
            "ODU Expected SAPI TTI (15 Characters)";
        }
        leaf odu-term {
          yang:get-supported "true";
          type enumeration {
            enum YES {
              description
                "Terminate ODU Layer";
            }
            enum NO {
              description
                "Not terminate ODU Layer";
            }
          }
          description
            "Indicating whether to terminate ODU Layer";
        }
        leaf odu-ex-dapi {
          yang:get-supported "true";
          type ciena-6500-types:STRING;
          description
            "ODU Expected DAPI TTI (15 Characters)";
        }
        leaf port-mode {
          yang:get-supported "true";
          type enumeration {
            enum SONET;
            enum SDH;
          }
          description
            "Optical port Market preference";
        }
        leaf odu-tf-mode {
          yang:get-supported "true";
          type enumeration {
            enum OFF {
              description
                "Alarms off, no traffic protection";
            }
            enum ALMONLY {
              description
                "Alarms on, no traffic protection";
            }
          }
          description
            "ODU Trace Fail Mode";
        }
        leaf trib-slot-assignment {
          yang:get-supported "true";
          type enumeration {
            enum "HEX value 00-FF";
          }
          description
            "This attribute is used to specify the value of transmitted tributary slots.";
        }
        leaf ex-ts {
          yang:get-supported "true";
          type enumeration {
            enum "HEX value 00-FF";
          }
          description
            "This attribute is used to specify the value of expected tributary slots.";
        }
        leaf rx-ts {
          yang:get-supported "true";
          type enumeration {
            enum "HEX value 00-FF";
          }
          description
            "This attribute is used to specify the value of actual received tributary slots.";
        }
        leaf odu-timen {
          yang:get-supported "true";
          type enumeration {
            enum OPERATOR {
              description
                "Monitor ODU Operator Specific TTI mismatch";
            }
            enum SAPI {
              description
                "Monitor ODU SAPI TTI mismatch";
            }
            enum DAPI {
              description
                "Monitor ODU DAPI TTI mismatch";
            }
            enum SAPI_DAPI {
              description
                "Monitor ODU SAPI and DAPI TTI mismatch";
            }
          }
          description
            "ODU TTI Mismatch Detection";
        }
        leaf odu-monitor {
          yang:get-supported "true";
          type enumeration {
            enum NO {
              description
                "ODU Monitoring off";
            }
            enum YES {
              description
                "ODU Monitoring on";
            }
          }
          description
            "ODU Monitor";
        }
        leaf trib-slot-prov {
          yang:get-supported "true";
          type enumeration {
            enum AUTO {
              description
                "The Rx trib slot is auto-detected by system. ";
            }
            enum MANUAL {
              description
                "The Rx trib slot is user specified. ";
            }
          }
          description
            "tribSlots provisioning mode";
        }
        leaf odu-flt-mon {
          yang:get-supported "true";
          type ciena-6500-types:STRING;
          description
            "ODU Fault Monitoring";
        }
        leaf odu-prf-mon {
          yang:get-supported "true";
          type ciena-6500-types:STRING;
          description
            "ODU Performance Monitoring";
        }
        leaf encryption-tcm {
          default "1";
          yang:get-supported "true";
          type ciena-6500-types:INT {
            range "1..6";
          }
          description
            "Active TCM Level for Encryption";
        }
        leaf encr-odu1 {
          yang:get-supported "true";
          type ciena-6500-types:INT;
          description
            "ODU Reserve Byte 1 for Encryption";
        }
        leaf ains-time-left {
          yang:get-supported "true";
          type ciena-6500-types:TIME;
          description
            "The format will be \"HH-MM\" for the time left in AINS timeout.";
        }
        leaf clfi {
          yang:get-supported "true";
          type ciena-6500-types:STRING;
          description
            "Common Language Facility Identifier. Customer provisionable label for an ODU facility.";
        }
        leaf pst {
          yang:get-supported "true";
          type ciena-6500-enums:PSTfac_RTRV;
          description
            "Identify the primary State";
        }
        leaf-list sst {
          yang:get-supported "true";
          type ciena-6500-enums:SSTODU;
          description
            "Secondary State";
        }
      }
    }
  }

  rpc port-disable-odu {
    description
      "Remove an ODU Facility";
    yang:handler "tl1";
    input {
      leaf odun {
        mandatory true;
        description
          "AID in format ODU0-shelf-slot-port-payloadindex, ODU1-shelf-slot-port-payloadindex, ODUFLEX-shelf-slot-port-payloadindex, ODU4-shelf-slot-port-index";
        type ciena-6500-types:aid;
      }
      leaf sst {
        type ciena-6500-enums:RMVSSTMT;
        description
          "Identify the Maintenance State";
      }
    }
  }

  rpc port-enable-odu {
    description
      "Restore an ODU Facility";
    yang:handler "tl1";
    input {
      leaf odun {
        mandatory true;
        description
          "AID in format ODU0-shelf-slot-port-payloadindex, ODU1-shelf-slot-port-payloadindex, ODUFLEX-shelf-slot-port-payloadindex, ODU4-shelf-slot-port-index";
        type ciena-6500-types:aid;
      }
    }
  }

  rpc port-show-pc {
    description
      "Retrieve the PC Facility attributes.";
    yang:handler "tl1";
    input {
      leaf pc {
        mandatory true;
        description
          "AID in format PC-shelf-slot-port, PC-shelf-slotSsubslot-port, PC-shelf-ALL, PC-shelf-slot-ALL, PC-shelf-slotSsubslot-ALL, SHELF-shelf-ALL, ALL";
        type ciena-6500-types:aid;
      }
    }
    output {
      list output {
        leaf pc {
          yang:get-supported "true";
          type ciena-6500-types:IDENT;
          description
            "aid";
        }
        leaf port-label {
          yang:get-supported "true";
          type ciena-6500-types:STRING;
          description
            "Port Label";
        }
        leaf port-select {
          yang:get-supported "true";
          type ciena-6500-types:STRING;
          description
            "The provisioned port of the CP to direct traffic towards";
        }
        leaf pst {
          yang:get-supported "true";
          type ciena-6500-enums:PSTfac_RTRV;
          description
            "Identify the primary state";
        }
        leaf-list sst {
          yang:get-supported "true";
          type ciena-6500-enums:SSTfac;
          description
            "Identify the secondary state";
        }
      }
    }
  }

  rpc port-show-facgrp {
    description
      "Retrieve the FACGRP facility parameters";
    yang:handler "tl1";
    input {
      leaf facgrp {
        mandatory true;
        description
          "AID in format FACGRP-shelf-grpIx, FACGRP-shelf-ALL, SHELF-shelf-ALL, ALL";
        type ciena-6500-types:aid;
      }
      leaf stats-info {
        yang:get-supported "true";
        type ciena-6500-enums:StatsInfoDefYes;
        description
          "Specify if Dynamic Status Information is to be included in the response.";
      }
    }
    output {
      list output {
        leaf facgrp {
          yang:get-supported "true";
          type ciena-6500-types:IDENT;
          description
            "aid";
        }
        leaf service-type {
          yang:get-supported "true";
          type ciena-6500-enums:facgrpServiceType;
          description
            "Configured Service Type";
        }
        leaf label {
          yang:get-supported "true";
          type string {
            length "0..64";
          }
          description
            "User specified Label";
        }
        leaf-list mbrlst {
          yang:get-supported "true";
          type ciena-6500-types:aid;
          description
            "List of FACGRP member AIDs.";
        }
        leaf minlatency {
          yang:get-supported "true";
          type string {
            length "0..64";
          }
          description
            "Minimum latency of the group";
        }
        leaf maxlatency {
          yang:get-supported "true";
          type string {
            length "0..64";
          }
          description
            "Maximum latency of the group";
        }
        leaf pst {
          yang:get-supported "true";
          type ciena-6500-enums:PSTfac_RTRV;
          description
            "Identify the primary State";
        }
      }
    }
  }

  rpc port-show-facgrpmbr {
    description
      "Retrieve the FACGRP member parameters";
    yang:handler "tl1";
    input {
      leaf facgrpmbr {
        mandatory true;
        description
          "AID in format FACGRPMBR-shelf-grpIx-mbrIx, FACGRPMBR-shelf-grpIx-ALL, FACGRPMBR-shelf-ALL, ALL";
        type ciena-6500-types:aid;
      }
      leaf stats-info {
        yang:get-supported "true";
        type ciena-6500-enums:StatsInfoDefYes;
        description
          "Specify if Dynamic Status Information is to be included in the response.";
      }
    }
    output {
      list output {
        leaf facgrpmbr {
          yang:get-supported "true";
          type ciena-6500-types:IDENT;
          description
            "aid";
        }
        leaf mbraid {
          yang:get-supported "true";
          type ciena-6500-types:aid;
          description
            "Facility AID of this member.";
        }
        leaf mbrlatency {
          yang:get-supported "true";
          type string {
            length "0..64";
          }
          description
            "Member latency.";
        }
      }
    }
  }

  rpc port-show-wavelength-rules {
    description
      "Retrieve the OTS wavelength provisioning rules.";
    yang:handler "tl1";
    input {
      leaf otsaid {
        mandatory true;
        description
          "AID in format ALL, OTS-shelf-instance, SHELF-shelf-ALL, OTS-shelf-ALL";
        type ciena-6500-types:aid;
      }
    }
    output {
      list output {
        leaf otsaid {
          yang:get-supported "true";
          type ciena-6500-types:IDENT;
          description
            "aid";
        }
        leaf wl {
          yang:get-supported "true";
          type ciena-6500-types:INT {
            range "152877..156672";
          }
          description
            "Wavelength";
        }
        leaf-list permit {
          yang:get-supported "true";
          type ciena-6500-enums:WLRULES;
          description
            "Wavelength Provisioning Rules";
        }
      }
    }
  }

  rpc port-show-vcp {
    description
      "Retrieve a Virtual Connection Point (VCP)";
    yang:handler "tl1";
    input {
      leaf vcp {
        mandatory true;
        description
          "AID in format VCP-shelf-vcpIdx, VCP-shelf-vcpIdx-dir, VCP-shelf-ALL, ALL";
        type ciena-6500-types:aid;
      }
    }
    output {
      list output {
        leaf vcp {
          yang:get-supported "true";
          type ciena-6500-types:IDENT;
          description
            "VCP AID";
        }
        leaf vcp-dir {
          yang:get-supported "true";
          type ciena-6500-types:aid;
          description
            "VCP";
        }
        leaf application-type {
          yang:get-supported "true";
          type enumeration {
            enum NONE;
            enum SNCP;
            enum UNI_SNCP;
          }
          description
            "The Application Type which identifies whether it is used in a protection scheme or not";
        }
        leaf selector {
          yang:get-supported "true";
          type enumeration {
            enum FALSE {
              description
                "VCP is not acting as a selector";
            }
            enum TRUE {
              description
                "VCP is acting as a selector";
            }
          }
          description
            "Indicates if the VCP is acting as a selector or not";
        }
        leaf size {
          yang:get-supported "true";
          type ciena-6500-types:INT {
            range "1..80";
          }
          description
            "Indicates the number of rate based timeslots that can be connected to the VCP. This attribute has a value of 1 when the VCP is not part of a GTP.";
        }
        leaf fcc {
          yang:get-supported "true";
          type ciena-6500-types:aid;
          description
            "Reference to associated FCC, if applicable.";
        }
        leaf usage-state {
          yang:get-supported "true";
          type enumeration {
            enum IDLE;
            enum BUSY;
            enum ACTIVE;
          }
          description
            "The type for Usage State.";
        }
        leaf vcp-type {
          yang:get-supported "true";
          type ciena-6500-enums:EnumVCPTYPE;
          description
            "This attribute indicates the type of CTPs that can be connected to this VCP.";
        }
        leaf label {
          yang:get-supported "true";
          type string {
            length "0..64";
          }
          description
            "This attribute is a customized description.";
        }
        leaf gep {
          yang:get-supported "true";
          type enumeration {
            enum YES;
            enum NO;
          }
          description
            "Specifies whether this VCP end-point facility accepts Generict End Point (GEP) method.";
        }
        leaf gep-name {
          yang:get-supported "true";
          type string {
            length "1..64";
          }
          description
            "Specifies the Generict End Point (GEP) name.";
        }
        leaf bit-rate {
          yang:get-supported "true";
          type string {
            length "0..64";
          }
          description
            "Define the bit rate of flex in bps.";
        }
      }
    }
  }

  container port {
    yang:create-supported "false";
    yang:edit-supported "false";
    yang:delete-supported "false";
    yang:containerptr "false";
    container loopback {
      yang:create-supported "false";
      yang:edit-supported "false";
      yang:delete-supported "false";
      yang:containerptr "false";
      list otuttp {
        yang:handler "tl1";
        yang:create-supported "false";
        yang:get-supported "true";
        yang:edit-supported "false";
        yang:delete-supported "false";
        key "otu";
        config false;
        leaf otu {
          mandatory true;
          description
            "AID in format OTUTTP-shelf-slot-port, OTUTTP-shelf-slot-portSsubport, OTUTTP-shelf-slot-ALL, OTUTTP-shelf-ALL, OTUTTP-shelf-slot-portPsubport";
          type ciena-6500-types:aid;
        }
        leaf loopback-type {
          yang:get-supported "true";
          type enumeration {
            enum FACILITY {
              description
                "Signal looped toward the equipment";
            }
            enum TERMINAL {
              description
                "Signal looped away from the equipment";
            }
          }
          description
            "Loopback Type";
          config false;
        }
      }
      list sttp {
        yang:handler "tl1";
        yang:create-supported "false";
        yang:get-supported "true";
        yang:edit-supported "false";
        yang:delete-supported "false";
        key "sttp";
        config false;
        leaf sttp {
          mandatory true;
          description
            "AID in format STTP-shelf-slot-port, STTP-shelf-slot-ALL, STTP-shelf-ALL, STTP-shelf-slot-portSsubport, STTP-shelf-slotSsubslot-port, STTP-shelf-slotSsubslot-portSsubport";
          type ciena-6500-types:aid;
        }
        leaf loopback-type {
          yang:get-supported "true";
          type enumeration {
            enum FACILITY {
              description
                "Signal looped toward the equipment";
            }
            enum TERMINAL {
              description
                "Signal looped away from the equipment";
            }
          }
          description
            "Loopback Type";
          config false;
        }
      }
      list ettp {
        yang:handler "tl1";
        yang:create-supported "false";
        yang:get-supported "true";
        yang:edit-supported "false";
        yang:delete-supported "false";
        key "ettp";
        config false;
        leaf ettp {
          mandatory true;
          description
            "AID in format ETTP-shelf-slot-port, ETTP-shelf-slot-portSsubport, ETTP-shelf-slotSsubslot-portSsubport, ETTP-shelf-slotSsubslot-port, ETTP-shelf-slot-ALL, ETTP-shelf-ALL";
          type ciena-6500-types:aid;
        }
        leaf loopback-type {
          yang:get-supported "true";
          type enumeration {
            enum FACILITY {
              description
                "Signal looped toward the equipment";
            }
            enum TERMINAL {
              description
                "Signal looped away from the equipment";
            }
          }
          description
            "Loopback Type";
          config false;
        }
      }
      list oduttp {
        yang:handler "tl1";
        yang:create-supported "false";
        yang:get-supported "true";
        yang:edit-supported "false";
        yang:delete-supported "false";
        key "oduttp";
        config false;
        leaf oduttp {
          mandatory true;
          description
            "AID in format ODUTTP-shelf-slot-port-rt1Ptp1, ODUTTP-shelf-slot-port-rt1Ptp1-rt2Ptp2, ODUTTP-shelf-slot-port-rt1Ptp1-ALL, ODUTTP-shelf-slot-port-ALL, ODUTTP-shelf-slot-ALL, ODUTTP-shelf-ALL";
          type ciena-6500-types:aid;
        }
        leaf loopback-type {
          yang:get-supported "true";
          type enumeration {
            enum FACILITY {
              description
                "Signal looped toward the equipment";
            }
            enum TERMINAL {
              description
                "Signal looped away from the equipment";
            }
          }
          description
            "Loopback Type";
          config false;
        }
      }
      list oductp {
        yang:handler "tl1";
        yang:create-supported "false";
        yang:get-supported "true";
        yang:edit-supported "false";
        yang:delete-supported "false";
        key "oductp";
        config false;
        leaf oductp {
          mandatory true;
          description
            "AID in format ODUCTP-shelf-slot-port-rt1Ptp1, ODUCTP-shelf-slot-port-rt1Ptp1-rt2Ptp2, ODUCTP-shelf-slot-port-rt1Ptp1-rt2Ptp2-rt3Ptp3, ODUCTP-shelf-slot-port-rt1Ptp1-rt2Ptp2-rt3Ptp3-rt4Ptp4, ODUCTP-shelf-slot-portSsubport-rt1Ptp1, ODUCTP-shelf-slot-portPsubport-rt1Ptp1-rt2Ptp2, ODUCTP-shelf-slot-portPsubport-rt1Ptp1";
          type ciena-6500-types:aid;
        }
        leaf loopback-type {
          yang:get-supported "true";
          type enumeration {
            enum FACILITY {
              description
                "Signal looped toward the equipment";
            }
            enum TERMINAL {
              description
                "Signal looped away from the equipment";
            }
          }
          description
            "Loopback Type";
          config false;
        }
      }
      list pdh {
        yang:handler "tl1";
        yang:create-supported "false";
        yang:get-supported "true";
        yang:edit-supported "false";
        yang:delete-supported "false";
        key "pdh";
        config false;
        leaf pdh {
          mandatory true;
          description
            "AID in format PDH-shelf-slot-port-rt1Ptp1-rt2Ptp2, PDH-shelf-slot-port-rt1Ptp1-rt2Ptp2-rt3Ptp3, PDH-shelf-slot-port-rt1Ptp1-rt2Ptp2-rt3Ptp3-rt4Ptp4, PDH-shelf-slot-port-rt1Ptp1-rt2Ptp2-rt3Ptp3-rt4Ptp4-rt5Ptp5, PDH-shelf-slotSsubslot-port-rt1Ptp1, PDH-shelf-slotSsubslot-port-rt1Ptp1-rt2Ptp2, PDH-shelf-slotSsubslot-port-rt1Ptp1-rt2Ptp2-rt3Ptp3, PDH-shelf-slotSsubslot-port-rt1Ptp1-rt2Ptp2-rt3Ptp3-rt4Ptp4, PDH-shelf-slot-port-rt1Ptp1, PDH-shelf-slot-ALL, PDH-shelf-slot-port-ALL, PDH-shelf-slotSsubslot-ALL, PDH-shelf-slotSsubslot-port-ALL, PDH-shelf-ALL";
          type ciena-6500-types:aid;
        }
        leaf loopback-locn {
          yang:get-supported "true";
          type ciena-6500-enums:LpbkLocn;
          description
            "Loopback Location";
          config false;
        }
        leaf loopback-type {
          yang:get-supported "true";
          type ciena-6500-enums:PDH_lpbk;
          description
            "Loopback Type";
          config false;
        }
        leaf lpbk-remlpbk {
          yang:get-supported "true";
          type ciena-6500-enums:RemLpbk;
          description
            "Remote loopback is allowed or inhibited";
          config false;
        }
      }
      list path {
        yang:handler "tl1";
        yang:create-supported "false";
        yang:get-supported "true";
        yang:edit-supported "false";
        yang:delete-supported "false";
        key "path";
        config false;
        leaf path {
          mandatory true;
          description
            "AID in format PATH-shelf-slot-port-rt1Ptp1, PATH-shelf-slot-port-rt1Ptp1-rt2Ptp2, PATH-shelf-slot-port-rt1Ptp1-rt2Ptp2-rt3Ptp3, PATH-shelf-slot-port-rt1Ptp1-rt2Ptp2-rt3Ptp3-rt4Ptp4, PATH-shelf-slotSsubslot-port-rt1Ptp1, PATH-shelf-slotSsubslot-port-rt1Ptp1-rt2Ptp2-rt3Ptp3, PATH-shelf-slot-ALL, PATH-shelf-slot-port-ALL, PATH-shelf-slotSsubslot-ALL, PATH-shelf-slotSsubslot-port-ALL, PATH-shelf-ALL";
          type ciena-6500-types:aid;
        }
        leaf loopback-type {
          yang:get-supported "true";
          type ciena-6500-enums:FLEXLoopBack;
          description
            "Loopback Type";
          config false;
        }
      }
      list cbrttp {
        yang:handler "tl1";
        yang:create-supported "false";
        yang:get-supported "true";
        yang:edit-supported "false";
        yang:delete-supported "false";
        key "cbrttp";
        config false;
        leaf cbrttp {
          mandatory true;
          description
            "AID in format CBRTTP-shelf-slot-port";
          type ciena-6500-types:aid;
        }
        leaf loopback-type {
          yang:get-supported "true";
          type enumeration {
            enum FACILITY {
              description
                "Signal looped toward the equipment";
            }
            enum TERMINAL {
              description
                "Signal looped away from the equipment";
            }
          }
          description
            "Loopback Type";
          config false;
        }
      }
    }
    container tti {
      yang:create-supported "false";
      yang:edit-supported "false";
      yang:delete-supported "false";
      yang:containerptr "false";
      list odu {
        yang:handler "tl1";
        yang:create-supported "false";
        yang:get-supported "true";
        yang:edit-supported "false";
        yang:delete-supported "false";
        key "odun";
        config false;
        leaf odun {
          mandatory true;
          description
            "AID in format ODU0-shelf-slot-port-payloadindex, ODU1-shelf-slot-port-payloadindex, ODUFLEX-shelf-slot-port-payloadindex, ODU4-shelf-slot-port-index";
          type ciena-6500-types:aid;
        }
        leaf tti-message {
          yang:get-supported "true";
          type ciena-6500-types:STRING;
          description
            "Trail Trace Identifier message";
          config false;
        }
      }
    }
    container wavelength {
      yang:create-supported "false";
      yang:edit-supported "false";
      yang:delete-supported "false";
      yang:containerptr "false";
      list rules {
        yang:handler "tl1";
        yang:create-supported "false";
        yang:get-supported "true";
        yang:edit-supported "false";
        yang:delete-supported "false";
        key "otsaid";
        config false;
        leaf otsaid {
          mandatory true;
          description
            "AID in format ALL, OTS-shelf-instance, SHELF-shelf-ALL, OTS-shelf-ALL";
          type ciena-6500-types:aid;
        }
        leaf wl {
          yang:get-supported "true";
          type ciena-6500-types:INT {
            range "152877..156672";
          }
          description
            "Wavelength";
          config false;
        }
        leaf-list permit {
          yang:get-supported "true";
          type ciena-6500-enums:WLRULES;
          description
            "Wavelength Provisioning Rules";
          config false;
        }
      }
    }
    list wan {
      yang:handler "tl1";
      yang:create-supported "true";
      yang:get-supported "true";
      yang:edit-supported "true";
      yang:delete-supported "true";
      key "wan";
      config true;
      leaf wan {
        mandatory true;
        description
          "AID in format WAN-shelf-slot-port, WAN-shelf-slot-portSsubport, WAN-shelf-slot-port-rt1Ptp1, WAN-shelf-slot-port-rt1Ptp1-rt2Ptp2, WAN-shelf-slot-port-rt1Ptp1-rt2Ptp2-rt3Ptp3, WAN-shelf-slot-port-rt1Ptp1-rt2Ptp2-rt3Ptp3-rt4Ptp4, WAN10G-shelf-slot-portSsubport, WAN-shelf-slot-portSsubport-rt1Ptp1, WAN-shelf-slot-portSsubport-rt1Ptp1-rt2Ptp2, WAN-shelf-slotSsubslot-portSsubport, WAN-shelf-slotSsubslot-port, WAN-shelf-slotSsubslot-portSsubport-rt1Ptp1, WAN-shelf-slotSsubslot-portSsubport-rt1Ptp1-rt2Ptp2, WAN-shelf-slotSsubslot-port-rt1Ptp1, WAN-shelf-slotSsubslot-port-rt1Ptp1-rt2Ptp2, WAN-shelf-slotSsubslot-port-rt1Ptp1-rt2Ptp2-rt3Ptp3";
        type ciena-6500-types:aid;
      }
      leaf magic-num {
        yang:create-supported "true";
        yang:get-supported "true";
        yang:edit-supported "true";
        yang:delete-supported "false";
        type enumeration {
          enum DISABLE;
          enum ENABLE;
        }
        description
          "Enables or disables the use of a magic number to distinguish between two peers and detect error conditions. Can be used to determine whether trying to establish a link with one self. Default value is Enable for MAPPING=POS, and Disable for MAPPING=GFP-F or GFP-T. For MAPPING=GFP-F or GFP-T, only possible value is Disable.";
        config true;
      }
      leaf fcs {
        yang:create-supported "true";
        yang:get-supported "true";
        yang:edit-supported "true";
        yang:delete-supported "false";
        type enumeration {
          enum 0;
          enum 16;
          enum 32;
        }
        default "0";
        description
          "Frame Checksum. For MAPPING=POS, value can be 16 or 32. For MAPPING=GFP-F, value can be 0 or 32. For MAPPING=GFP-T, the only possible value is 0.";
        config true;
      }
      leaf scramble {
        yang:create-supported "false";
        yang:get-supported "true";
        yang:edit-supported "true";
        yang:delete-supported "false";
        type enumeration {
          enum ENABLE;
          enum DISABLE;
        }
        description
          "Used to control payload X^43+1 payload scrambling.";
        config true;
      }
      leaf lcm {
        yang:create-supported "true";
        yang:get-supported "true";
        yang:edit-supported "true";
        yang:delete-supported "false";
        type enumeration {
          enum DISABLE;
          enum ENABLE;
        }
        description
          "Link Connectivity Monitor. In some circumstances it may be desirable to disable the link continuity monitor (LCM). When enabled, LCM sends an echo request every second. If more than five echo requests are transmitted without receiving an echo response, the PPP operational OSI state becomes disabled, and PPP attempts to re-establish the link connection via LCP configuration request packets. Default value is Enable for MAPPING=POS, and Disable for MAPPING=GFP-F or GFP-T. For MAPPING=GFP-F or GFP-T, only possible value is Disable.";
        config true;
      }
      leaf mapping {
        yang:create-supported "true";
        yang:get-supported "true";
        yang:edit-supported "true";
        yang:delete-supported "false";
        type enumeration {
          enum POS;
          enum GFP-F;
          enum GFP-T;
        }
        default "GFP-F";
        description
          "Sonnet Mapping Protocol - Editing of this attribute will be rejected.";
        config true;
      }
      leaf-list vcat {
        yang:create-supported "true";
        yang:get-supported "true";
        yang:edit-supported "true";
        yang:delete-supported "false";
        type enumeration {
          enum DISABLE;
          enum ENABLE;
          enum GROUPED {
            description
              "Grouped switching enabled (from dual sources).";
          }
        }
        description
          "Virtual SONET/SDH concatenation";
        config true;
      }
      leaf lcas {
        yang:create-supported "true";
        yang:get-supported "true";
        yang:edit-supported "true";
        yang:delete-supported "false";
        type enumeration {
          enum DISABLE {
            description
              "Default";
          }
          enum ENABLE {
            description
              "ENABLE can only be set if vcat is enable";
          }
        }
        default "DISABLE";
        description
          "Link Capacity Adjustment Scheme Mode";
        config true;
      }
      leaf lan-fcs {
        yang:create-supported "true";
        yang:get-supported "true";
        yang:edit-supported "true";
        yang:delete-supported "false";
        type enumeration {
          enum DISABLE;
          enum ENABLE;
        }
        description
          "Indicates whether the LAN FCS is included in the encapsulated frame (for both the ingress and egress direction). Enable indicates the LAN FCS is included. Default value is Enable for MAPPING=POS, and Disable for MAPPING=GFP-F or GFP-T. For MAPPING=GFP-F or GFP-T, only possible value is Disable.";
        config true;
      }
      leaf cond-type {
        yang:create-supported "true";
        yang:get-supported "true";
        yang:edit-supported "true";
        yang:delete-supported "false";
        type enumeration {
          enum NONE {
            description
              "Only valid value for 10GOTR/10GOTSC";
          }
          enum GFPCMF {
            description
              "GFP CMF is transmitted for conditioning";
          }
          enum GFPCMFUSER {
            description
              "Transmit user specified GFP CMF and GFP IDLE toward line";
          }
          enum GFP10BERR {
            description
              "Transmit GFP 10B_ERR symbols in the GFP frame";
          }
          enum UNEQ {
            description
              "P-UNEQ is transmitted on WAN for conditioning";
          }
          enum NILTR {
            description
              "Nil (empty) path trace will be sent to the backplane when WAN conditioning is required.";
          }
          enum AIS {
            description
              "AIS will transmit SONET/SDH Path AIS on WAN when conditioning is required.";
          }
          enum GFPCSF {
            description
              "GFP CSF is transmitted for conditioning";
          }
        }
        description
          "This attribute is used to control the type of WAN conditioning applied to WAN upon LAN defects (Rx Loss of Signal, Rx Loss of Sync, AN time-out, Rx Idle, Link Down) and CP Fail. Possible values are NONE or a combination of: GFPCMF,GFPCMFUSER, GFP10BERR, UNEQ, AIS and NILTR.";
        config true;
      }
      leaf gfp-cmf-upi {
        yang:create-supported "true";
        yang:get-supported "true";
        yang:edit-supported "true";
        yang:delete-supported "false";
        type ciena-6500-types:STRING;
        description
          "HEX value in the range 0x03-0xFF. UPI to be transmitted in GFP client management frames.";
        config true;
      }
      leaf if-type {
        yang:create-supported "true";
        yang:get-supported "true";
        yang:edit-supported "true";
        yang:delete-supported "false";
        type enumeration {
          enum UNI;
          enum NNI;
        }
        description
          "The interface type of the WAN facility being created.";
        config true;
      }
      leaf policing {
        yang:create-supported "true";
        yang:get-supported "true";
        yang:edit-supported "true";
        yang:delete-supported "false";
        type enumeration {
          enum ENABLE;
          enum DISABLE;
        }
        default "ENABLE";
        description
          "Indicates whether policing will be done on the given port";
        config true;
      }
      leaf e-type {
        yang:create-supported "true";
        yang:get-supported "true";
        yang:edit-supported "true";
        yang:delete-supported "false";
        type string {
          length "1..4";
        }
        description
          "Encapsulation scheme used in customer frames";
        config true;
      }
      leaf dm-prf {
        yang:create-supported "true";
        yang:get-supported "true";
        yang:edit-supported "true";
        yang:delete-supported "false";
        type ciena-6500-types:STRING;
        description
          "(DEPRECATED) Discard Marking Profile";
        config true;
      }
      leaf cf-prf {
        yang:create-supported "true";
        yang:get-supported "true";
        yang:edit-supported "true";
        yang:delete-supported "false";
        type ciena-6500-types:STRING;
        description
          "Control Frame Profile (CFPRF-shelf-profileNo)";
        config true;
      }
      leaf sch-prf {
        yang:create-supported "true";
        yang:get-supported "true";
        yang:edit-supported "true";
        yang:delete-supported "false";
        type ciena-6500-types:STRING;
        description
          "(DEPRECATED) Scheduler Profile";
        config true;
      }
      leaf loop-detect {
        yang:create-supported "true";
        yang:get-supported "true";
        yang:edit-supported "true";
        yang:delete-supported "false";
        type enumeration {
          enum ENABLE;
          enum DISABLE;
        }
        default "DISABLE";
        description
          "Loopback Detection using SONMP.";
        config true;
      }
      leaf p-mode {
        yang:create-supported "false";
        yang:get-supported "true";
        yang:edit-supported "true";
        yang:delete-supported "false";
        type enumeration {
          enum PBITS;
          enum TOS;
        }
        description
          "(DEPRECATED) Priority mode";
        config true;
      }
      leaf bw-threshld {
        yang:create-supported "true";
        yang:get-supported "true";
        yang:edit-supported "true";
        yang:delete-supported "false";
        type ciena-6500-types:INT {
          range "1..100";
        }
        description
          "The bandwidth utilization percentage threshold ";
        config true;
      }
      leaf gfp-rfi {
        yang:create-supported "true";
        yang:get-supported "true";
        yang:edit-supported "true";
        yang:delete-supported "false";
        type enumeration {
          enum ENABLE {
            description
              "Transmit GFP RFI CMF on WAN link down";
          }
          enum DISABLE {
            description
              " Do not transmit CMF UPI on WAN link down(only possible value for FC)";
          }
          enum CMFCSF {
            description
              "Transmit GFP CSF CMF on WAN link down";
          }
          enum USERDEF {
            description
              "Transmit userdefined UPI value one WAN link down.";
          }
        }
        description
          "Control the transmission of GFP Client Signal Fail (CSF) CMFs. ENABLE is the default for Ethernet. Disable is the defaults and only possible value for FC";
        config true;
      }
      leaf gfp-rfi-upi {
        yang:create-supported "true";
        yang:get-supported "true";
        yang:edit-supported "true";
        yang:delete-supported "false";
        type ciena-6500-types:INT {
          range "3..255";
        }
        description
          "Transmits user defined UPI value on WAN link down. ";
        config true;
      }
      leaf gfp-rt-delay {
        yang:create-supported "true";
        yang:get-supported "true";
        yang:edit-supported "true";
        yang:delete-supported "false";
        type enumeration {
          enum ENABLE;
          enum DISABLE;
        }
        description
          "GFP round trip delay. Setting to DISABLE means the ping CMFs used for RTDELAY calculation and Distance Exceeded Alarm will no longer be sent. This implies RTDELAY will always display UNKNOWN and the Distance Exceeded Alarm will never raise. This is a way to disable the usage of the proprietary CMFs. Default=ENABLE";
        config true;
      }
      leaf opu2-resvd {
        yang:create-supported "false";
        yang:get-supported "true";
        yang:edit-supported "true";
        yang:delete-supported "false";
        type enumeration {
          enum YES {
            description
              "Use 7 unused bytes of the OPU2 overhead for payload.";
          }
          enum NO {
            description
              "Do not use 7 unused bytes of the OPU2 overhead for payload";
          }
        }
        description
          "This attribute is used to specify whether to use the 7 unused bytes of the OPU2 overhead for payload or not.";
        config true;
      }
      leaf fcs-err-frames {
        yang:create-supported "true";
        yang:get-supported "true";
        yang:edit-supported "true";
        yang:delete-supported "false";
        type enumeration {
          enum KEEP {
            description
              "Keep FCS-errored frames end-to-end.";
          }
          enum DISCARD {
            description
              "Discard FCS-errored frames end-to-end.";
          }
        }
        default "DISCARD";
        description
          "This attribute is used to specify whether to keep FCS-errored frames or Ethernet frames end-to-end or to discard them.";
        config true;
      }
      leaf-list pdh-type {
        yang:create-supported "true";
        yang:get-supported "true";
        yang:edit-supported "true";
        yang:delete-supported "false";
        type ciena-6500-enums:PDHTYPE_LIST;
        description
          "PDH channel type associated with WAN. Supported on L2SS-PDH only.";
        config true;
      }
      leaf exp-pt {
        yang:create-supported "false";
        yang:get-supported "true";
        yang:edit-supported "true";
        yang:delete-supported "false";
        type ciena-6500-types:STRING;
        description
          "HEX value in the range 0x00-0xFF. This attribute is used to specify the value of Expected PT.";
        config true;
      }
      leaf tx-pt {
        yang:create-supported "false";
        yang:get-supported "true";
        yang:edit-supported "true";
        yang:delete-supported "false";
        type ciena-6500-types:STRING;
        description
          "HEX value in the range 0x00-0xFF. This attribute is used to specify the value of Transmitted PT.";
        config true;
      }
      leaf expected-upi {
        yang:create-supported "false";
        yang:get-supported "true";
        yang:edit-supported "true";
        yang:delete-supported "false";
        type ciena-6500-types:STRING;
        description
          "HEX value in the range 0x00-0xFF. This attribute is used to specify the value of Expected UPI.";
        config true;
      }
      leaf tx-upi {
        yang:create-supported "false";
        yang:get-supported "true";
        yang:edit-supported "true";
        yang:delete-supported "false";
        type ciena-6500-types:STRING;
        description
          "HEX value in the range 0x00-0xFF. This attribute is used to specify the value of Transmitted UPI.";
        config true;
      }
      leaf q-grp-1 {
        yang:create-supported "true";
        yang:get-supported "true";
        yang:edit-supported "true";
        yang:delete-supported "false";
        type ciena-6500-types:STRING;
        description
          "The AID of the queue group profile (QGRP-shelf-profileNo) to be used for queue group 1.";
        config true;
      }
      leaf q-grp-2 {
        yang:create-supported "true";
        yang:get-supported "true";
        yang:edit-supported "true";
        yang:delete-supported "false";
        type ciena-6500-types:STRING;
        description
          "The AID of the queue group profile (QGRP-shelf-profileNo) to be used for queue group 2.";
        config true;
      }
      leaf tx-cos-profile {
        yang:create-supported "true";
        yang:get-supported "true";
        yang:edit-supported "true";
        yang:delete-supported "false";
        type ciena-6500-types:STRING;
        description
          "The AID of the port TX COS Profile (TXCOSPRF-shelf-profileNo)";
        config true;
      }
      leaf rx-cos-profile {
        yang:create-supported "true";
        yang:get-supported "true";
        yang:edit-supported "true";
        yang:delete-supported "false";
        type ciena-6500-types:STRING;
        description
          "The AID of the port RX COS Profile (RXCOSPRF-shelf-profileNo)";
        config true;
      }
      leaf user-rx-cos {
        yang:create-supported "true";
        yang:get-supported "true";
        yang:edit-supported "true";
        yang:delete-supported "false";
        type ciena-6500-types:INT {
          range "0..15";
        }
        description
          "The IPHB value to map the untagged frames";
        config true;
      }
      leaf pbt-list-sup {
        yang:create-supported "true";
        yang:get-supported "true";
        yang:edit-supported "true";
        yang:delete-supported "false";
        type ciena-6500-types:INT {
          range "0 | 1";
        }
        description
          "Indicates the PBT VID list support on WAN facility";
        config true;
      }
      leaf pdh-vli {
        yang:create-supported "true";
        yang:get-supported "true";
        yang:edit-supported "true";
        yang:delete-supported "false";
        type enumeration {
          enum DISABLE {
            description
              "Default - VLI overhead octet used for data";
          }
          enum ENABLE {
            description
              "VLI overhead octet set to zeros.";
          }
        }
        description
          "This attribute is used to specify VLI octet usage for PDH WANs. VLI=Vcat Lcas Interworking, the concatenation overhead octet.";
        config true;
      }
      leaf mac-option {
        yang:create-supported "true";
        yang:get-supported "true";
        yang:edit-supported "true";
        yang:delete-supported "false";
        type enumeration {
          enum NONE {
            description
              "No MAC provisioned on the facility.";
          }
          enum MANUAL {
            description
              "MAC manually provisioned on the facility.";
          }
          enum AUTO {
            description
              "MAC automatically assigned to the facility.";
          }
        }
        description
          "The MAC provisioning option";
        config true;
      }
      leaf mac {
        yang:create-supported "true";
        yang:get-supported "true";
        yang:edit-supported "true";
        yang:delete-supported "false";
        type ciena-6500-types:IDENT;
        description
          "48-bit Ethernet MAC address displayed as 12 alphanumeric characters. Unique to each facility.";
        config true;
      }
      leaf os-tran {
        yang:create-supported "false";
        yang:get-supported "true";
        yang:edit-supported "true";
        yang:delete-supported "false";
        type enumeration {
          enum NONE {
            description
              "None";
          }
          enum LEGACYCMF {
            description
              "Proprietary Legacy Client Managed Frame.";
          }
          enum G7041CMF {
            description
              "G704.1 standard GFP Client Management Frame.";
          }
          enum G7041CDF {
            description
              "G704.1 standard GFP Client Data Frame.";
          }
        }
        description
          "This attribute is used to specify whether the WAN facility supports Ordered Set Transparency for G704.1 compliance.";
        config true;
      }
      leaf pst {
        yang:create-supported "true";
        yang:get-supported "true";
        yang:edit-supported "false";
        yang:delete-supported "false";
        type enumeration {
          enum IS {
            description
              "(This value can be used in create operation)";
          }
          enum OOS-MA {
            description
              "(This value can be used in create operation)";
          }
          enum IS-ANR {
            description
              "In Service - Abnormal";
          }
          enum OOS-AU {
            description
              "Out-of-service autonomous from a failure detected point of view. It is not out of service from a state point of view. Alarm is raised if the entity is not able to perform its provisioned functions";
          }
          enum OOS-AUMA {
            description
              "Out-of-service autonomous management - the entity is not able to perform its provisioned functions and is purposefully removed from service";
          }
          enum OOS-MAANR {
            description
              "Out-of-service maintenance - abnormal.";
          }
        }
        default "OOS-MA";
        description
          "Primary State of the WAN object";
        config true;
      }
      leaf mode {
        yang:create-supported "false";
        yang:get-supported "true";
        yang:edit-supported "false";
        yang:delete-supported "false";
        type enumeration {
          enum SDH;
          enum SONET;
        }
        description
          "Indicates the current mode (either SONET or SDH).";
        config false;
      }
      leaf rate {
        yang:create-supported "false";
        yang:get-supported "true";
        yang:edit-supported "false";
        yang:delete-supported "false";
        type enumeration {
          enum NONE {
            description
              "SONET/SDH Basic rate derived from SONET/SDH cross-connections";
          }
          enum STS1 {
            description
              "SONET/SDH Basic rate derived from SONET/SDH cross-connections";
          }
          enum STS3C {
            description
              "SONET/SDH Basic rate derived from SONET/SDH cross-connections";
          }
          enum STS6C {
            description
              "SONET/SDH Basic rate derived from SONET/SDH cross-connections";
          }
          enum STS9C {
            description
              "SONET/SDH Basic rate derived from SONET/SDH cross-connections";
          }
          enum STS12C {
            description
              "SONET/SDH Basic rate derived from SONET/SDH cross-connections";
          }
          enum STS24C {
            description
              "SONET/SDH Basic rate derived from SONET/SDH cross-connections";
          }
          enum STS48C {
            description
              "SONET/SDH Basic rate derived from SONET/SDH cross-connections";
          }
          enum STS192C {
            description
              "SONET/SDH Basic rate derived from SONET/SDH cross-connections";
          }
          enum VT1 {
            description
              "SONET/SDH Basic rate derived from SONET/SDH cross-connections";
          }
          enum VT2 {
            description
              "SONET/SDH Basic rate derived from SONET/SDH cross-connections";
          }
        }
        description
          "SONET/SDH Basic rate (derived from SONET/SDH cross-connections)";
        config false;
      }
      leaf prov-units {
        yang:create-supported "false";
        yang:get-supported "true";
        yang:edit-supported "false";
        yang:delete-supported "false";
        type ciena-6500-types:INT {
          range "0..64";
        }
        description
          "Used to indicate the number of provisioned bandwidth units (of rate specified by the RATE attribute). Number of provisioned bandwidth units (RATE attributes). For contiguous concatenation, allowable values are either 0 or 1. The information is derived from the cross connection(s).";
        config false;
      }
      leaf prov-rx-units {
        yang:create-supported "false";
        yang:get-supported "true";
        yang:edit-supported "false";
        yang:delete-supported "false";
        type ciena-6500-types:INT {
          range "0..64";
        }
        description
          "Indicate the current number of provisioned members in the receive direction.";
        config false;
      }
      leaf actual-units {
        yang:create-supported "false";
        yang:get-supported "true";
        yang:edit-supported "false";
        yang:delete-supported "false";
        type ciena-6500-types:INT {
          range "0..64";
        }
        description
          "Indicates the number of bandwidth units actually carrying traffic. For contiguous concatenation, or for virtual concatenation without LCAS enabled, allowable values are either 0 or PROVUNITS. With LCAS enabled, allowable values are 0 to PROVUNITS. If the value cannot be retrieved, UNKNOWN will be displayed.";
        config false;
      }
      leaf ncp {
        yang:create-supported "false";
        yang:get-supported "true";
        yang:edit-supported "false";
        yang:delete-supported "false";
        type enumeration {
          enum NONE;
          enum BCP;
        }
        description
          "Used to indicate the Network Control Protocol used. BCP is returned when MAPPING=POS, and NONE is returned when MAPPING=GFP=F or GFP-T.";
        config false;
      }
      leaf max-vc-del {
        yang:create-supported "false";
        yang:get-supported "true";
        yang:edit-supported "false";
        yang:delete-supported "false";
        type ciena-6500-types:INT {
          range "0..256000";
        }
        description
          "Maximum differential delay supported by the port in microseconds. If the value cannot be retrieved, UNKNOWN will be displayed.";
        config false;
      }
      leaf curr-vc-del {
        yang:create-supported "false";
        yang:get-supported "true";
        yang:edit-supported "false";
        yang:delete-supported "false";
        type ciena-6500-types:INT {
          range "0..256000";
        }
        description
          "Current differential delay in microseconds. If the value cannot be retrieved, UNKNOWN will be displayed. If VCAT is disabled or if WAN is not cross-connected, NA (Not Applicable) will be displayed.";
        config false;
      }
      leaf round-trip-delay {
        yang:create-supported "false";
        yang:get-supported "true";
        yang:edit-supported "false";
        yang:delete-supported "false";
        type ciena-6500-types:INT {
          range "0..220000";
        }
        description
          "Round Trip Delay in microseconds. If the value cannot be retrieved, UNKNOWN will be displayed.";
        config false;
      }
      leaf actual-rx-units {
        yang:create-supported "false";
        yang:get-supported "true";
        yang:edit-supported "false";
        yang:delete-supported "false";
        type ciena-6500-types:INT {
          range "0..64";
        }
        description
          "Current number of active members in the receive direction. When LCAS is disabled, allowable values are either 0 or PROVRXUNITS. With LCAS enabled, allowable values are 0 to PROVRXUNITS. If the value cannot be retrieved, UNKNOWN will be displayed.";
        config false;
      }
      leaf-list available-rate {
        yang:create-supported "false";
        yang:get-supported "true";
        yang:edit-supported "false";
        yang:delete-supported "false";
        type enumeration {
          enum RATE {
            description
              "The available bandwidth for a given port (in SONET/SDH Basic RATE) For Ex : In GE card VCAT=ENABLE. AVLBLRATE on all WAN ports is STS1LO/STS1HO/STS3C ";
          }
        }
        description
          "Used to indicate the available bandwidth rate in the wan port.";
        config false;
      }
      leaf bw-remain {
        yang:create-supported "false";
        yang:get-supported "true";
        yang:edit-supported "false";
        yang:delete-supported "false";
        type ciena-6500-types:INT {
          range "1..2500000";
        }
        description
          "The unused bandwidth remained for a given port (in KBIT)";
        config false;
      }
      leaf bw-utl {
        yang:create-supported "false";
        yang:get-supported "true";
        yang:edit-supported "false";
        yang:delete-supported "false";
        type ciena-6500-types:INT {
          range "0..100";
        }
        description
          "The port bandwidth utilization percentage";
        config false;
      }
      leaf snmp-index {
        yang:create-supported "false";
        yang:get-supported "true";
        yang:edit-supported "false";
        yang:delete-supported "false";
        type ciena-6500-types:INT {
          range "0..4294967295";
        }
        description
          "Identifies the index of the equivalent entry in the SNMP interfaces MIB group";
        config false;
      }
      leaf preamble {
        yang:create-supported "false";
        yang:get-supported "true";
        yang:edit-supported "false";
        yang:delete-supported "false";
        type enumeration {
          enum KEEP {
            description
              "Keep Ethernet preamble.";
          }
          enum DISCARD {
            description
              "Discard Ethernet preamble.";
          }
        }
        description
          "This attribute is used to specify whether to use the preamble at beginning of GFP frame or throw it away. The preamble is 8 bytes in total (7 bytes + 1 byte sfd).";
        config false;
      }
      leaf received-pt {
        yang:create-supported "false";
        yang:get-supported "true";
        yang:edit-supported "false";
        yang:delete-supported "false";
        type ciena-6500-types:STRING;
        description
          "HEX value in the range 0x00-0xFF. This attribute is used for Received PT";
        config false;
      }
      leaf received-upi {
        yang:create-supported "false";
        yang:get-supported "true";
        yang:edit-supported "false";
        yang:delete-supported "false";
        type ciena-6500-types:STRING;
        description
          "HEX value in the range 0x00-0xFF. This attribute is used for Received UPI";
        config false;
      }
      leaf wan-cap {
        yang:create-supported "false";
        yang:get-supported "true";
        yang:edit-supported "false";
        yang:delete-supported "false";
        type enumeration {
          enum HICAP {
            description
              "WAN port supports rate up to STS-192";
          }
          enum MEDCAP {
            description
              "WAN port supports rate up to STS-24";
          }
          enum LOCAP {
            description
              "WAN port supports rate up to STS-3";
          }
        }
        description
          "This attribute indicates the capacity of the WAN port";
        config false;
      }
      leaf supported-term-pt {
        yang:create-supported "false";
        yang:get-supported "true";
        yang:edit-supported "false";
        yang:delete-supported "false";
        type ciena-6500-types:STRING;
        description
          "Facility AID format. The supporting Termination Point.";
        config false;
      }
      leaf direction {
        yang:create-supported "false";
        yang:get-supported "true";
        yang:edit-supported "false";
        yang:delete-supported "false";
        type enumeration {
          enum RX {
            description
              "Monitoring receive direction";
          }
          enum TX {
            description
              "Monitoring transmit direction";
          }
        }
        description
          "Monitoring GFP layer in receive or transmit direction";
        config false;
      }
      leaf reserved {
        yang:create-supported "false";
        yang:get-supported "true";
        yang:edit-supported "false";
        yang:delete-supported "false";
        type ciena-6500-enums:BOOL_YES_NO;
        description
          "Specify if the facility is being reserved for packet SNC's";
        config false;
      }
      leaf rxmon {
        yang:create-supported "false";
        yang:get-supported "true";
        yang:edit-supported "false";
        yang:delete-supported "false";
        type ciena-6500-enums:BOOL_YES_NO_defaultNO;
        description
          "Indicate if the signal is monitored in the Rx direction for alarms and PMs and OMs.";
        config false;
      }
      leaf rxterm {
        yang:create-supported "false";
        yang:get-supported "true";
        yang:edit-supported "false";
        yang:delete-supported "false";
        type ciena-6500-enums:BOOL_YES_NO_defaultNO;
        description
          "Indicate if the signal is terminated in the Rx direction or not.";
        config false;
      }
      leaf tx-mon {
        yang:create-supported "false";
        yang:get-supported "true";
        yang:edit-supported "false";
        yang:delete-supported "false";
        type ciena-6500-enums:BOOL_YES_NO_defaultNO;
        description
          "Indicate if the signal is monitored in the Tx direction for alarms and PMs and OMs.";
        config false;
      }
      leaf tx-term {
        yang:create-supported "false";
        yang:get-supported "true";
        yang:edit-supported "false";
        yang:delete-supported "false";
        type ciena-6500-enums:BOOL_YES_NO_defaultNO;
        description
          "Indicate if the signal is terminated in the Tx direction for alarms and PMs and OMs.";
        config false;
      }
      leaf-list sst {
        yang:create-supported "false";
        yang:get-supported "true";
        yang:edit-supported "false";
        yang:delete-supported "false";
        type enumeration {
          enum AINS {
            description
              "Auto-In-Service";
          }
          enum AINS-DEA {
            description
              "Auto-In-Service-Deactivate";
          }
          enum MT {
            description
              "Maintenance";
          }
          enum ACT {
            description
              "Active, carrying traffic";
          }
          enum DISCD {
            description
              "Idle, not carrying traffic";
          }
          enum FLT {
            description
              "Fault detected in equipment";
          }
          enum SGEO {
            description
              "Supporting entity outage";
          }
          enum WRKRX {
            description
              "Working in the receive direction";
          }
          enum WRKTX {
            description
              "Working in the transmit direction";
          }
          enum UEQ {
            description
              "Unequipped";
          }
          enum MEA {
            description
              "Mismatched equipment attributes";
          }
          enum DSBLD {
            description
              "Missing layer 2 connection; Idle, not carrying traffic";
          }
          enum UAS {
            description
              "RPR WAN only, Not associated to an RPR SPAN";
          }
        }
        description
          "Identify the secondary state";
        config false;
      }
      leaf force {
        yang:create-supported "false";
        yang:get-supported "false";
        yang:edit-supported "true";
        yang:delete-supported "false";
        type enumeration {
          enum NO {
            description
              "Do Not Force Edit";
          }
          enum YES {
            description
              "Force Traffic Impacting Edit";
          }
        }
        default "NO";
        description
          "Indicating whether to force an edit when facility still in service (traffic impacting)";
        config true;
      }
    }
    list eth10g {
      yang:handler "tl1";
      yang:create-supported "true";
      yang:get-supported "true";
      yang:edit-supported "true";
      yang:delete-supported "true";
      key "eth10g";
      config true;
      leaf eth10g {
        mandatory true;
        description
          "AID in format ETH10G-shelf-slot-port, ETH10G-shelf-slot-portSsubport";
        type ciena-6500-types:aid;
      }
      leaf laser-off-far-end-fail {
        yang:create-supported "true";
        yang:get-supported "true";
        yang:edit-supported "true";
        yang:delete-supported "false";
        type ciena-6500-enums:Laserofffarendfail;
        default "DISABLED";
        description
          "Enable or Disable LOL (Loss of Light) feature";
        config true;
      }
      leaf mtu {
        yang:create-supported "true";
        yang:get-supported "true";
        yang:edit-supported "true";
        yang:delete-supported "false";
        type ciena-6500-enums:MTU;
        description
          "Maximum Ethernet frame size supported. Setting the MTU size will influence the distance lossless local flow control is supported (the smaller the MTU, the larger the lossless distance).";
        config true;
      }
      leaf flow-ctrl {
        yang:create-supported "true";
        yang:get-supported "true";
        yang:edit-supported "true";
        yang:delete-supported "false";
        type ciena-6500-enums:FLOWCTRL;
        description
          "Advertised flow control capabilities.";
        config true;
      }
      leaf auto-neg {
        yang:create-supported "true";
        yang:get-supported "true";
        yang:edit-supported "true";
        yang:delete-supported "false";
        type enumeration {
          enum ENABLE;
          enum DISABLE {
            description
              "Always Disable for 10GE.";
          }
        }
        default "DISABLE";
        description
          "Auto-negotiation, R/W, only one value supported=DISABLE on 10GE.";
        config true;
      }
      leaf pause-tx {
        yang:create-supported "true";
        yang:get-supported "true";
        yang:edit-supported "true";
        yang:delete-supported "false";
        type enumeration {
          enum ENABLE;
          enum DISABLE;
        }
        default "ENABLE";
        description
          "Controls PAUSE transmission when AN is disabled. Ignored when AN is enabled.";
        config true;
      }
      leaf speed {
        yang:create-supported "true";
        yang:get-supported "true";
        yang:edit-supported "true";
        yang:delete-supported "false";
        type enumeration {
          enum 10G {
            description
              "Always 10G for 10GE";
          }
        }
        default "10G";
        description
          "Only one value is allowed, Always 10G.";
        config true;
      }
      leaf eth-duplex {
        yang:create-supported "true";
        yang:get-supported "true";
        yang:edit-supported "true";
        yang:delete-supported "false";
        type enumeration {
          enum FULL {
            description
              "Always FULL for 10GE";
          }
          enum HALF;
          enum BOTH;
        }
        default "FULL";
        description
          "Advertised duplex operation capabilities if AN is enabled.";
        config true;
      }
      leaf tx-con {
        yang:create-supported "true";
        yang:get-supported "true";
        yang:edit-supported "true";
        yang:delete-supported "false";
        type enumeration {
          enum ENABLE;
          enum DISABLE;
        }
        default "ENABLE";
        description
          "Control the EPL conditioning. Enabling will turn off the GigE laser when Ethernet conditioning is required. Disabling will prevent Ethernet conditioning (i.e. the GigE laser will remain enabled) as a result of SONET/SDH path failure, as well as GFP failures and GFP RFI/CSF client management frame reception.";
        config true;
      }
      leaf tx-inter-pkt-gap {
        yang:create-supported "true";
        yang:get-supported "true";
        yang:edit-supported "true";
        yang:delete-supported "false";
        type enumeration {
          enum 11;
          enum 12;
        }
        default "12";
        description
          "Tx Inter-Packet Gap. 12 is the default value.";
        config true;
      }
      leaf tx-con-hb {
        yang:create-supported "true";
        yang:get-supported "true";
        yang:edit-supported "true";
        yang:delete-supported "false";
        type enumeration {
          enum DISABLE;
          enum ENABLE;
          enum TXONLY;
        }
        default "ENABLE";
        description
          "Used to control conditioning of client ports through Heartbeat mechanism with remote using Y.1731 CCM PDUs.";
        config true;
      }
      leaf tx-con-hb-interval {
        yang:create-supported "true";
        yang:get-supported "true";
        yang:edit-supported "true";
        yang:delete-supported "false";
        type enumeration {
          enum 100MSEC;
          enum 1SEC;
        }
        default "1SEC";
        description
          "Tx Conditioning Heartbeat Interval";
        config true;
      }
      leaf tx-con-md-level {
        default "0";
        yang:create-supported "true";
        yang:get-supported "true";
        yang:edit-supported "true";
        yang:delete-supported "false";
        type ciena-6500-types:INT {
          range "0..7";
        }
        description
          "Tx Conditioning MD Level";
        config true;
      }
      leaf tx-cond-network-flt-sig {
        yang:create-supported "true";
        yang:get-supported "true";
        yang:edit-supported "true";
        yang:delete-supported "false";
        type enumeration {
          enum TLV;
          enum EXPLICIT;
          enum CFM;
        }
        default "EXPLICIT";
        description
          "Tx Conditioning Network Fault Signal";
        config true;
      }
      leaf eqpt {
        yang:create-supported "true";
        yang:get-supported "true";
        yang:edit-supported "true";
        yang:delete-supported "false";
        type enumeration {
          enum XGELAN;
          enum XGEWAN;
        }
        default "XGELAN";
        description
          "Interface equipment type.";
        config true;
      }
      leaf pause-tx-override {
        yang:create-supported "true";
        yang:get-supported "true";
        yang:edit-supported "true";
        yang:delete-supported "false";
        type enumeration {
          enum ENABLE;
          enum DISABLE {
            description
              "Always DISABLE for 10GE";
          }
        }
        default "DISABLE";
        description
          "Controls PAUSE reception when AN is disabled. Ignored when AN is enabled.";
        config true;
      }
      leaf rx-idle {
        yang:create-supported "true";
        yang:get-supported "true";
        yang:edit-supported "true";
        yang:delete-supported "false";
        type enumeration {
          enum 0;
          enum 1;
          enum 2;
          enum 3;
          enum 4;
          enum 5;
          enum 10;
          enum 60;
          enum 120;
          enum 300;
        }
        default "0";
        description
          "Always 0 for 10GE.";
        config true;
      }
      leaf dm-prf {
        yang:create-supported "true";
        yang:get-supported "true";
        yang:edit-supported "true";
        yang:delete-supported "false";
        type ciena-6500-types:STRING;
        description
          "(DEPRECATED) Discard Marking Profile";
        config true;
      }
      leaf cf-prf {
        yang:create-supported "true";
        yang:get-supported "true";
        yang:edit-supported "true";
        yang:delete-supported "false";
        type ciena-6500-types:STRING;
        description
          "The AID of the port Control Frame Profile (CFPRF-shelf-profileNo)";
        config true;
      }
      leaf sch-prf {
        yang:create-supported "true";
        yang:get-supported "true";
        yang:edit-supported "true";
        yang:delete-supported "false";
        type ciena-6500-types:STRING;
        description
          "(DEPRECATED) Scheduler Profiler";
        config true;
      }
      leaf policing {
        yang:create-supported "true";
        yang:get-supported "true";
        yang:edit-supported "true";
        yang:delete-supported "false";
        type enumeration {
          enum ENABLE;
          enum DISABLE;
        }
        description
          "Indicates whether policing will be done on the given port";
        config true;
      }
      leaf e-type {
        yang:create-supported "true";
        yang:get-supported "true";
        yang:edit-supported "true";
        yang:delete-supported "false";
        type string {
          length "1..4";
        }
        description
          "Encapsulation scheme used in customer frames";
        config true;
      }
      leaf latency-opt {
        yang:create-supported "true";
        yang:get-supported "true";
        yang:edit-supported "true";
        yang:delete-supported "false";
        type enumeration {
          enum MINIMUM;
          enum MEDIUM;
          enum MAXIMUM;
        }
        description
          "Latency Optimization";
        config true;
      }
      leaf sync-status-msg-transmit {
        yang:create-supported "true";
        yang:get-supported "true";
        yang:edit-supported "true";
        yang:delete-supported "false";
        type ciena-6500-enums:SSMTRANSMIT;
        description
          "Synchronized Status Messaging Transmit.";
        config true;
      }
      leaf dus-override {
        yang:create-supported "true";
        yang:get-supported "true";
        yang:edit-supported "true";
        yang:delete-supported "false";
        type enumeration {
          enum ENABLE;
          enum DISABLE;
        }
        default "DISABLE";
        description
          "A parameter which allows the synchronization quality level of a line reference to be overriden even when the receiving quality level is DUS.";
        config true;
      }
      leaf rx-cos-profile {
        yang:create-supported "true";
        yang:get-supported "true";
        yang:edit-supported "true";
        yang:delete-supported "false";
        type ciena-6500-types:STRING;
        description
          "The AID of the port RX COS Profile (RXCOSPRF-shelf-profileNo)";
        config true;
      }
      leaf tx-cos-profile {
        yang:create-supported "true";
        yang:get-supported "true";
        yang:edit-supported "true";
        yang:delete-supported "false";
        type ciena-6500-types:STRING;
        description
          "The AID of the port TX COS Profile (TXCOSPRF-shelf-profileNo)";
        config true;
      }
      leaf user-rx-cos {
        yang:create-supported "true";
        yang:get-supported "true";
        yang:edit-supported "true";
        yang:delete-supported "false";
        type ciena-6500-types:INT {
          range "0..15";
        }
        description
          "The IPHB value to map the untagged frames";
        config true;
      }
      leaf q-grp-1 {
        yang:create-supported "true";
        yang:get-supported "true";
        yang:edit-supported "true";
        yang:delete-supported "false";
        type ciena-6500-types:STRING;
        description
          "The AID of the queue group profile (QGRP-shelf-profileNo) to be used for queue group 1.";
        config true;
      }
      leaf q-grp-2 {
        yang:create-supported "true";
        yang:get-supported "true";
        yang:edit-supported "true";
        yang:delete-supported "false";
        type ciena-6500-types:STRING;
        description
          "The AID of the queue group profile (QGRP-shelf-profileNo) to be used for queue group 2.";
        config true;
      }
      leaf port-bw {
        yang:create-supported "true";
        yang:get-supported "true";
        yang:edit-supported "true";
        yang:delete-supported "false";
        type ciena-6500-types:STRING;
        description
          "The AID of the bandwidth profile (BWPRF-shelf-profileNo).";
        config true;
      }
      leaf pbt-list-sup {
        yang:create-supported "true";
        yang:get-supported "true";
        yang:edit-supported "true";
        yang:delete-supported "false";
        type ciena-6500-types:INT {
          range "0 | 1";
        }
        description
          "Indicates the PBT VID list support on Ethernet facility";
        config true;
      }
      leaf rate {
        yang:create-supported "true";
        yang:get-supported "true";
        yang:edit-supported "true";
        yang:delete-supported "false";
        type ciena-6500-types:INT {
          range "10 | 20 | 30..10000";
        }
        description
          "The EVPL bandwidth rate.";
        config true;
      }
      leaf clfi {
        yang:create-supported "true";
        yang:get-supported "true";
        yang:edit-supported "true";
        yang:delete-supported "false";
        type ciena-6500-types:STRING;
        description
          "Common Language Facility Identifier.Customer provisionable label for a facility.";
        config true;
      }
      leaf hold-off {
        yang:create-supported "true";
        yang:get-supported "true";
        yang:edit-supported "true";
        yang:delete-supported "false";
        type ciena-6500-types:INT {
          range "0 | 100 | 200 | 300 | 400 | 500 | 600 | 700 | 800 | 900 | 1000";
        }
        description
          "Conditioning holdoff time in milliseconds.";
        config true;
      }
      leaf tx-wvlngth-prov {
        yang:create-supported "true";
        yang:get-supported "true";
        yang:edit-supported "true";
        yang:delete-supported "false";
        type ciena-6500-types:STRING;
        description
          "Provisioned Wavelength in nm (xxxx.xx)";
        config true;
      }
      leaf lldpmon {
        yang:create-supported "true";
        yang:get-supported "true";
        yang:edit-supported "true";
        yang:delete-supported "false";
        type ciena-6500-enums:LLDPMON_REFID;
        description
          "Specifies if facility is monitoring LLDP packets or not.";
        config true;
      }
      leaf-list sst {
        yang:create-supported "true";
        yang:get-supported "true";
        yang:edit-supported "true";
        yang:delete-supported "false";
        type enumeration {
          enum AINS {
            description
              "Auto-In-Service(This value can be used in create and edit operations)";
          }
          enum AINS-DEA {
            description
              "Auto-In-Service Deactivate(This value can be used in create and edit operations)";
          }
          enum MT {
            description
              "Maintenance(This value can be used in create operation)";
          }
          enum FLT {
            description
              "Fault detected in equipment";
          }
          enum LPBK {
            description
              "Loopback";
          }
          enum SGEO {
            description
              "Supporting entity outage";
          }
          enum DISCD {
            description
              "Disconnected. (no transparent traffic connection on this facility)";
          }
          enum TSGEN {
            description
              "Test set generation";
          }
          enum TSMON {
            description
              "Test set monitor";
          }
        }
        description
          "Identify the secondary state";
        config true;
      }
      leaf if-type {
        yang:create-supported "true";
        yang:get-supported "true";
        yang:edit-supported "false";
        yang:delete-supported "false";
        type enumeration {
          enum UNI;
          enum NNI;
        }
        description
          "The type of the ETH10G facility being queried";
        config true;
      }
      leaf mapping {
        yang:create-supported "true";
        yang:get-supported "true";
        yang:edit-supported "false";
        yang:delete-supported "false";
        type enumeration {
          enum PROP237 {
            description
              "proportional 11.09";
          }
          enum PROP238 {
            description
              "proportional 11.05";
          }
          enum GFPMACTR {
            description
              "GFP-F mapped, MAC transparent";
          }
          enum GFPSTD {
            description
              "GFP-F mapped, Standard WAN";
          }
          enum GFPMACTR192 {
            description
              "GFP-F mapped, MAC transparent, port mode of layer facility is SONET";
          }
          enum GFPSTD192 {
            description
              "GFP-F mapped, Standard WAN, port mode of layer facility is SONET";
          }
          enum GFPMACTR64 {
            description
              "GFP-F mapped, MAC transparent, port mode of layer facility is SDH";
          }
          enum GFPSTD64 {
            description
              "GFP-F mapped, Standard WAN, port mode of layer facility is SDH";
          }
          enum GFPMACOSTR {
            description
              "GFP-F mapped, Ordered Set MAC transparent";
          }
          enum GFPMACOSTR192 {
            description
              "GFP-F mapped, Ordered Set MAC transparent, port mode of layer facility is SONET";
          }
          enum GFPMACOSTR64 {
            description
              "GFP-F mapped, Ordered Set MAC transparent, port mode of layer facility is SDH";
          }
          enum NONE {
            description
              "Not mapped";
          }
          enum ULL {
            description
              "Ultra Low Latency";
          }
        }
        default "GFPSTD";
        description
          "The mapping layer OTM2 OTURATE and client mapping";
        config true;
      }
      leaf mode {
        yang:create-supported "true";
        yang:get-supported "true";
        yang:edit-supported "false";
        yang:delete-supported "false";
        type enumeration {
          enum L2;
          enum EVPL;
        }
        default "L2";
        description
          "The mode of service.";
        config true;
      }
      leaf pst {
        yang:create-supported "true";
        yang:get-supported "true";
        yang:edit-supported "false";
        yang:delete-supported "false";
        type enumeration {
          enum IS {
            description
              "In Service(This value can be used in create operation)";
          }
          enum IS-ANR {
            description
              "In Service - Abnormal";
          }
          enum OOS-MA {
            description
              "Out-of-service maintenance for provisioning memory administration(This value can be used in create operation)";
          }
          enum OOS-AU {
            description
              "Out-of-service autonomous from a failure detected point of view. It is not out of service from a state point of view. Alarm is raised if the entity is not able to perform its provisioned functions";
          }
          enum OOS-AUMA {
            description
              "Out-of-service autonomous management - the entity is not able to perform its provisioned functions and is purposefully removed from service";
          }
          enum OOS-MAANR {
            description
              "Out-of-service maintenance - abnormal";
          }
        }
        default "IS";
        description
          "Identify the primary state";
        config true;
      }
      leaf tx-act-pwr {
        yang:create-supported "false";
        yang:get-supported "true";
        yang:edit-supported "false";
        yang:delete-supported "false";
        type ciena-6500-types:STRING;
        description
          "TX actual power in dBm (xx.x)";
        config false;
      }
      leaf tx-min-pwr {
        yang:create-supported "false";
        yang:get-supported "true";
        yang:edit-supported "false";
        yang:delete-supported "false";
        type ciena-6500-types:STRING;
        description
          "TX minimum power in dBm (xx.x)";
        config false;
      }
      leaf tx-max-pwr {
        yang:create-supported "false";
        yang:get-supported "true";
        yang:edit-supported "false";
        yang:delete-supported "false";
        type ciena-6500-types:STRING;
        description
          "TX maximum power in dBm (xx.x)";
        config false;
      }
      leaf rx-act-pwr {
        yang:create-supported "false";
        yang:get-supported "true";
        yang:edit-supported "false";
        yang:delete-supported "false";
        type ciena-6500-types:STRING;
        description
          "RX actual power in dBm (xx.x)";
        config false;
      }
      leaf rx-min-pwr {
        yang:create-supported "false";
        yang:get-supported "true";
        yang:edit-supported "false";
        yang:delete-supported "false";
        type ciena-6500-types:STRING;
        description
          "RX minimum power in dBm (xx.x)";
        config false;
      }
      leaf rx-max-pwr {
        yang:create-supported "false";
        yang:get-supported "true";
        yang:edit-supported "false";
        yang:delete-supported "false";
        type ciena-6500-types:STRING;
        description
          "RX maximum power in dBm (xx.x)";
        config false;
      }
      leaf an-status {
        yang:create-supported "false";
        yang:get-supported "true";
        yang:edit-supported "false";
        yang:delete-supported "false";
        type enumeration {
          enum INPROGRESS;
          enum COMPLETED;
          enum DISABLED;
          enum UNKNOWN {
            description
              "Always UNKNOWN for 10GE.";
          }
        }
        description
          "Auto-negotiation status";
        config false;
      }
      leaf pause-rx {
        yang:create-supported "false";
        yang:get-supported "true";
        yang:edit-supported "false";
        yang:delete-supported "false";
        type enumeration {
          enum ENABLE;
          enum DISABLE {
            description
              "Always DISABLE for 10GE";
          }
        }
        description
          "Controls PAUSE reception when AN is disabled. Ignored when AN is enabled.";
        config false;
      }
      leaf pause-rx-override {
        yang:create-supported "false";
        yang:get-supported "true";
        yang:edit-supported "false";
        yang:delete-supported "false";
        type enumeration {
          enum ENABLE;
          enum DISABLE;
        }
        description
          "If AN is enabled, and ANPAUSERX is negotiated to enable, setting this attribute to enable means received PAUSE frames will not be acted upon. They will either be discarded or pass through transparently (based on the PASSCTRL setting).";
        config false;
      }
      leaf an-eth-duplex {
        yang:create-supported "false";
        yang:get-supported "true";
        yang:edit-supported "false";
        yang:delete-supported "false";
        type enumeration {
          enum FULL;
          enum HALF;
          enum BOTH;
          enum UNKNOWN {
            description
              "Always UNKNOWN for 10GE";
          }
        }
        description
          "Negotiated Duplex Operation, when AN is enabled.";
        config false;
      }
      leaf an-speed {
        yang:create-supported "false";
        yang:get-supported "true";
        yang:edit-supported "false";
        yang:delete-supported "false";
        type enumeration {
          enum 10G;
          enum UNKNOWN {
            description
              "Always UNKNOWN for 10GE.";
          }
        }
        description
          "Negotiated speed, when AN is enabled.";
        config false;
      }
      leaf an-pause-tx {
        yang:create-supported "false";
        yang:get-supported "true";
        yang:edit-supported "false";
        yang:delete-supported "false";
        type enumeration {
          enum ENABLE;
          enum DISABLE;
          enum UNKNOWN {
            description
              "Always UNKNOWN for 10GE.";
          }
        }
        description
          "Negotiated PAUSE transmit, when AN is enabled.";
        config false;
      }
      leaf an-pause-rx {
        yang:create-supported "false";
        yang:get-supported "true";
        yang:edit-supported "false";
        yang:delete-supported "false";
        type enumeration {
          enum ENABLE;
          enum DISABLE;
          enum UNKNOWN {
            description
              "Always UNKNOWN for 10GE.";
          }
        }
        description
          "Negotiated PAUSE receive, when AN is enabled.";
        config false;
      }
      leaf adv-eth-duplex {
        yang:create-supported "false";
        yang:get-supported "true";
        yang:edit-supported "false";
        yang:delete-supported "false";
        type enumeration {
          enum FULL;
          enum HALF;
          enum BOTH;
          enum UNKNOWN {
            description
              "Always UNKNOWN for 10GE.";
          }
        }
        description
          "Link partner advertised Duplex capabilities. Only valid when ANSTATUS is COMPLETED.";
        config false;
      }
      leaf adv-speed {
        yang:create-supported "false";
        yang:get-supported "true";
        yang:edit-supported "false";
        yang:delete-supported "false";
        type enumeration {
          enum 10G;
          enum UNKNOWN {
            description
              "Always UNKNOWN for 10GE.";
          }
        }
        description
          "Link partner advertised speed capabilities. Only valid when ANSTATUS is COMPLETED.";
        config false;
      }
      leaf adv-flow-ctrl {
        yang:create-supported "false";
        yang:get-supported "true";
        yang:edit-supported "false";
        yang:delete-supported "false";
        type enumeration {
          enum NONE;
          enum ASYM;
          enum SYM;
          enum UNKNOWN {
            description
              "Always UNKNOWN for 10GE";
          }
        }
        description
          "Link partner advertised flow control capabilities. Only valid when ANSTATUS is COMPLETED.";
        config false;
      }
      leaf pass-ctrl {
        yang:create-supported "false";
        yang:get-supported "true";
        yang:edit-supported "false";
        yang:delete-supported "false";
        type enumeration {
          enum ENABLE;
          enum DISABLE {
            description
              "Always DISABLE for 10GE.";
          }
        }
        description
          "Controls whether transmitted Ethernet Control Frames (T/L=8808) are passed transparently (Enable), or removed from the flow (Disable).";
        config false;
      }
      leaf phys-addr {
        yang:create-supported "false";
        yang:get-supported "true";
        yang:edit-supported "false";
        yang:delete-supported "false";
        type ciena-6500-types:IDENT;
        description
          "48-bit Ethernet MAC address displayed as 12 alphanumeric characters. Used as SA in PAUSE frames.";
        config false;
      }
      leaf cbr-bw-remain {
        yang:create-supported "false";
        yang:get-supported "true";
        yang:edit-supported "false";
        yang:delete-supported "false";
        type ciena-6500-types:STRING;
        description
          "CBR Bandwidth Remain";
        config false;
      }
      leaf lag-id {
        yang:create-supported "false";
        yang:get-supported "true";
        yang:edit-supported "false";
        yang:delete-supported "false";
        type ciena-6500-types:STRING;
        description
          "The AID of the LAG to which the given ETH10G port belongs.";
        config false;
      }
      leaf timing-ref {
        yang:create-supported "false";
        yang:get-supported "true";
        yang:edit-supported "false";
        yang:delete-supported "false";
        type enumeration {
          enum N {
            description
              "Not a timing reference";
          }
          enum Y {
            description
              "Is a timing reference";
          }
        }
        description
          "Indicates whether the ETH10G facility is a timing reference";
        config false;
      }
      leaf ains-time-left {
        yang:create-supported "false";
        yang:get-supported "true";
        yang:edit-supported "false";
        yang:delete-supported "false";
        type ciena-6500-types:TIME;
        description
          "The format will be HH-MM for the time left in AINS timeout.";
        config false;
      }
      leaf tx-wvlngth-min {
        default "0.00";
        yang:create-supported "false";
        yang:get-supported "true";
        yang:edit-supported "false";
        yang:delete-supported "false";
        type ciena-6500-types:STRING;
        description
          "Minimum Wavelength value in nm (xxxx.xx)";
        config false;
      }
      leaf tx-wvlngth-max {
        default "0.00";
        yang:create-supported "false";
        yang:get-supported "true";
        yang:edit-supported "false";
        yang:delete-supported "false";
        type ciena-6500-types:STRING;
        description
          "Maximum Wavelength value in nm (xxxx.xx)";
        config false;
      }
      leaf tx-wvlngth-spacing {
        yang:create-supported "false";
        yang:get-supported "true";
        yang:edit-supported "false";
        yang:delete-supported "false";
        type ciena-6500-types:STRING;
        description
          "OCH Wavelength Spacing in Ghz";
        config false;
      }
      leaf spli-mgmt {
        yang:create-supported "false";
        yang:get-supported "true";
        yang:edit-supported "false";
        yang:delete-supported "false";
        type ciena-6500-enums:spliMgmt;
        description
          "Identify if Port is Manageable by SPLI";
        config false;
      }
      leaf spli-managed {
        yang:create-supported "false";
        yang:get-supported "true";
        yang:edit-supported "false";
        yang:delete-supported "false";
        type ciena-6500-enums:spliManaged;
        description
          "Identify if Port is Currently Managed by SPLI";
        config false;
      }
    }
    list ethn {
      yang:handler "tl1";
      yang:create-supported "true";
      yang:get-supported "true";
      yang:edit-supported "true";
      yang:delete-supported "true";
      key "ethn";
      config true;
      leaf ethn {
        mandatory true;
        description
          "AID in format ETH100G-shelf-slot-port, ETH40G-shelf-slot-port";
        type ciena-6500-types:aid;
      }
      leaf laser-off-far-end-fail {
        yang:create-supported "true";
        yang:get-supported "true";
        yang:edit-supported "true";
        yang:delete-supported "false";
        type ciena-6500-enums:Laserofffarendfail;
        default "DISABLED";
        description
          "Enable the feature of laser off far end fail";
        config true;
      }
      leaf clfi {
        yang:create-supported "true";
        yang:get-supported "true";
        yang:edit-supported "true";
        yang:delete-supported "false";
        type ciena-6500-types:STRING;
        description
          "Common Language Facility Identifier.Customer provisionable label for a facility.";
        config true;
      }
      leaf mtu {
        yang:create-supported "true";
        yang:get-supported "true";
        yang:edit-supported "true";
        yang:delete-supported "false";
        type ciena-6500-enums:MTU;
        description
          "Maximum Ethernet frame size supported. Setting the MTU size will influence the distance lossless local flow control is supported (the smaller the MTU, the larger the lossless distance).";
        config true;
      }
      leaf fec-frmt {
        yang:create-supported "true";
        yang:get-supported "true";
        yang:edit-supported "true";
        yang:delete-supported "false";
        type enumeration {
          enum OFF {
            description
              "NO FEC";
          }
          enum RS10 {
            description
              "RS10 FEC";
          }
        }
        description
          "FEC Format";
        config true;
      }
      leaf pre-fec-sf-th-lev {
        yang:create-supported "true";
        yang:get-supported "true";
        yang:edit-supported "true";
        yang:delete-supported "false";
        type decimal64 {
          range "-1.00..1.00";
          fraction-digits 2;
        }
        description
          "Pre-FEC Signal Fail Threshold Level (in dBQ).";
        config true;
      }
      leaf pre-fec-sd-th-lev {
        yang:create-supported "true";
        yang:get-supported "true";
        yang:edit-supported "true";
        yang:delete-supported "false";
        type decimal64 {
          range "-1.00..2.00";
          fraction-digits 2;
        }
        description
          "Pre-FEC Signal Degrade Threshold Level (in dBQ).";
        config true;
      }
      leaf hold-off {
        yang:create-supported "true";
        yang:get-supported "true";
        yang:edit-supported "true";
        yang:delete-supported "false";
        type ciena-6500-types:INT {
          range "0 | 100 | 200 | 300 | 400 | 500 | 600 | 700 | 800 | 900 | 1000";
        }
        description
          "Hold Off signal conditioning timer (in increments of 100).";
        config true;
      }
      leaf lldpmon {
        yang:create-supported "true";
        yang:get-supported "true";
        yang:edit-supported "true";
        yang:delete-supported "false";
        type ciena-6500-enums:LLDPMON_REFID;
        description
          "Specifies if facility is monitoring LLDP packets or not.";
        config true;
      }
      leaf-list sst {
        yang:create-supported "true";
        yang:get-supported "true";
        yang:edit-supported "true";
        yang:delete-supported "false";
        type enumeration {
          enum AINS {
            description
              "Auto-In-Service(This value can be used in create and edit operations)";
          }
          enum AINS-DEA {
            description
              "Auto-In-Service Deactivate(This value can be used in create and edit operations)";
          }
          enum MT {
            description
              "Maintenance(This value can be used in create operation)";
          }
          enum FLT {
            description
              "Fault detected in equipment";
          }
          enum LPBK {
            description
              "Loopback";
          }
          enum SGEO {
            description
              "Supporting entity outage";
          }
          enum DISCD {
            description
              "Disconnected (no transparent traffic connection on this facility)";
          }
          enum TSGEN {
            description
              "Test set generation";
          }
          enum TSMON {
            description
              "Test set monitor";
          }
        }
        description
          "Identify the secondary state";
        config true;
      }
      leaf mapping {
        yang:create-supported "true";
        yang:get-supported "true";
        yang:edit-supported "false";
        yang:delete-supported "false";
        type enumeration {
          enum GMP {
            description
              "GMP";
          }
          enum GFPFLEX {
            description
              "GFPFLEX mapping";
          }
          enum PROPRIETARY {
            description
              "PROPRIETARY";
          }
        }
        description
          "Mapping";
        config true;
      }
      leaf pst {
        yang:create-supported "true";
        yang:get-supported "true";
        yang:edit-supported "false";
        yang:delete-supported "false";
        type enumeration {
          enum IS {
            description
              "In Service(This value can be used in create operation)";
          }
          enum IS-ANR {
            description
              "In Service - Abnormal";
          }
          enum OOS-MA {
            description
              "Out-of-service maintenance for provisioning memory administration(This value can be used in create operation)";
          }
          enum OOS-AU {
            description
              "Out-of-service autonomous from a failure detected point of view. It is not out of service from a state point of view. Alarm is raised if the entity is not able to perform its provisioned functions";
          }
          enum OOS-AUMA {
            description
              "Out-of-service autonomous management - the entity is not able to perform its provisioned functions and is purposefully removed from service";
          }
          enum OOS-MAANR {
            description
              "Out-of-service maintenance - abnormal";
          }
        }
        default "IS";
        description
          "Identify the primary state";
        config true;
      }
      leaf-list tx-act-ln-pwr {
        yang:create-supported "false";
        yang:get-supported "true";
        yang:edit-supported "false";
        yang:delete-supported "false";
        type ciena-6500-types:STRING;
        description
          "Lanes TX Power(Format:Lane1|Lane2|...)";
        config false;
      }
      leaf tx-act-high-pwr {
        yang:create-supported "false";
        yang:get-supported "true";
        yang:edit-supported "false";
        yang:delete-supported "false";
        type ciena-6500-types:STRING;
        description
          "TX Actual High Power Value in dBm (xx.x)";
        config false;
      }
      leaf tx-act-low-pwr {
        yang:create-supported "false";
        yang:get-supported "true";
        yang:edit-supported "false";
        yang:delete-supported "false";
        type ciena-6500-types:STRING;
        description
          "TX Actual Low Power Value in dBm (xx.x)";
        config false;
      }
      leaf tx-min-pwr {
        yang:create-supported "false";
        yang:get-supported "true";
        yang:edit-supported "false";
        yang:delete-supported "false";
        type ciena-6500-types:STRING;
        description
          "TX minimum power in dBm (xx.x)";
        config false;
      }
      leaf tx-max-pwr {
        yang:create-supported "false";
        yang:get-supported "true";
        yang:edit-supported "false";
        yang:delete-supported "false";
        type ciena-6500-types:STRING;
        description
          "TX maximum power in dBm (xx.x)";
        config false;
      }
      leaf-list rx-act-ln-pwr {
        yang:create-supported "false";
        yang:get-supported "true";
        yang:edit-supported "false";
        yang:delete-supported "false";
        type ciena-6500-types:STRING;
        description
          "Lanes RX Power(Format:Lane1|Lane2|...)";
        config false;
      }
      leaf rx-act-high-pwr {
        yang:create-supported "false";
        yang:get-supported "true";
        yang:edit-supported "false";
        yang:delete-supported "false";
        type ciena-6500-types:STRING;
        description
          "RX Actual High Power Value in dBm (xx.x)";
        config false;
      }
      leaf rx-act-low-pwr {
        yang:create-supported "false";
        yang:get-supported "true";
        yang:edit-supported "false";
        yang:delete-supported "false";
        type ciena-6500-types:STRING;
        description
          "RX Actual Low Power Value in dBm (xx.x)";
        config false;
      }
      leaf rx-min-pwr {
        yang:create-supported "false";
        yang:get-supported "true";
        yang:edit-supported "false";
        yang:delete-supported "false";
        type ciena-6500-types:STRING;
        description
          "RX minimum power in dBm (xx.x)";
        config false;
      }
      leaf rx-max-pwr {
        yang:create-supported "false";
        yang:get-supported "true";
        yang:edit-supported "false";
        yang:delete-supported "false";
        type ciena-6500-types:STRING;
        description
          "RX maximum power in dBm (xx.x)";
        config false;
      }
      leaf ains-time-left {
        yang:create-supported "false";
        yang:get-supported "true";
        yang:edit-supported "false";
        yang:delete-supported "false";
        type ciena-6500-types:TIME;
        description
          "The format will be HH-MM for the time left in AINS timeout.";
        config false;
      }
      leaf member-1 {
        yang:create-supported "false";
        yang:get-supported "true";
        yang:edit-supported "false";
        yang:delete-supported "false";
        type ciena-6500-types:STRING;
        description
          "The AID of member 1 (FLEX-shelf-slot-port).";
        config false;
      }
      leaf member-2 {
        yang:create-supported "false";
        yang:get-supported "true";
        yang:edit-supported "false";
        yang:delete-supported "false";
        type ciena-6500-types:STRING;
        description
          "The AID of member 2 (FLEX-shelf-slot-port).";
        config false;
      }
      leaf member-3 {
        yang:create-supported "false";
        yang:get-supported "true";
        yang:edit-supported "false";
        yang:delete-supported "false";
        type ciena-6500-types:STRING;
        description
          "The AID of member 3 (FLEX-shelf-slot-port).";
        config false;
      }
      leaf member-4 {
        yang:create-supported "false";
        yang:get-supported "true";
        yang:edit-supported "false";
        yang:delete-supported "false";
        type ciena-6500-types:STRING;
        description
          "The AID of member 4 (FLEX-shelf-slot-port).";
        config false;
      }
      leaf pre-fec-sf-th-ber {
        yang:create-supported "false";
        yang:get-supported "true";
        yang:edit-supported "false";
        yang:delete-supported "false";
        type ciena-6500-types:STRING;
        description
          "Pre-FEC Signal Fail Threshold Bit Error Rate.";
        config false;
      }
      leaf pre-fec-sd-th-ber {
        yang:create-supported "false";
        yang:get-supported "true";
        yang:edit-supported "false";
        yang:delete-supported "false";
        type ciena-6500-types:STRING;
        description
          "Pre-FEC Signal Degrade Threshold Bit Error Rate.";
        config false;
      }
      leaf spli-mgmt {
        yang:create-supported "false";
        yang:get-supported "true";
        yang:edit-supported "false";
        yang:delete-supported "false";
        type ciena-6500-enums:spliMgmt;
        description
          "Identify if Port is Manageable by SPLI";
        config false;
      }
      leaf spli-managed {
        yang:create-supported "false";
        yang:get-supported "true";
        yang:edit-supported "false";
        yang:delete-supported "false";
        type ciena-6500-enums:spliManaged;
        description
          "Identify if Port is Currently Managed by SPLI";
        config false;
      }
    }
    list flex {
      yang:handler "tl1";
      yang:create-supported "true";
      yang:get-supported "true";
      yang:edit-supported "true";
      yang:delete-supported "true";
      key "flex";
      config true;
      leaf flex {
        mandatory true;
        description
          "AID in format FLEX-shelf-slot-port, FLEX-shelf-slot-portSsubport";
        type ciena-6500-types:aid;
      }
      leaf protocol {
        yang:create-supported "true";
        yang:get-supported "true";
        yang:edit-supported "false";
        yang:delete-supported "false";
        type ciena-6500-enums:PROTOCOL;
        mandatory true;
        description
          "Protocol";
        config true;
      }
      leaf rate {
        yang:create-supported "true";
        yang:get-supported "true";
        yang:edit-supported "true";
        yang:delete-supported "false";
        type ciena-6500-types:STRING;
        description
          "Protocol Rate, in Mbps. Supported values are 1000, 1062.5, 1250, 2125, 4250, 8500, and 10500.";
        config true;
      }
      leaf mapping {
        yang:create-supported "true";
        yang:get-supported "true";
        yang:edit-supported "true";
        yang:delete-supported "false";
        type ciena-6500-enums:FLEX_MAPPING;
        description
          "Mapping type";
        config true;
      }
      leaf latency-opt {
        yang:create-supported "true";
        yang:get-supported "true";
        yang:edit-supported "true";
        yang:delete-supported "false";
        type enumeration {
          enum MINIMUM;
          enum MEDIUM;
          enum MAXIMUM;
        }
        default "MEDIUM";
        description
          "Latency Optimization";
        config true;
      }
      leaf tx-con {
        yang:create-supported "true";
        yang:get-supported "true";
        yang:edit-supported "true";
        yang:delete-supported "false";
        type enumeration {
          enum LOFEF {
            description
              "Laser Off Far End Fail";
          }
          enum 8B10B {
            description
              "8B10B";
          }
          enum NOS {
            description
              "NOS";
          }
          enum AISL {
            description
              "AISL";
          }
          enum K30_7 {
            description
              "K30_7";
          }
          enum LF {
            description
              "Local Fault";
          }
          enum LNKFLTC1C2 {
            description
              "LNKFLTC1C2";
          }
        }
        description
          "TX conditioning";
        config true;
      }
      leaf hold-off {
        yang:create-supported "true";
        yang:get-supported "true";
        yang:edit-supported "true";
        yang:delete-supported "false";
        type ciena-6500-types:INT {
          range "0 | 100 | 200..2000";
        }
        description
          "Conditioning holdoff time in seconds.";
        config true;
      }
      leaf tf-mode {
        yang:create-supported "true";
        yang:get-supported "true";
        yang:edit-supported "true";
        yang:delete-supported "false";
        type enumeration {
          enum OFF {
            description
              "Alarms off, no traffic protection";
          }
          enum ALMONLY {
            description
              "Alarms on, no traffic protection";
          }
          enum LINEFAIL {
            description
              "Alarms on, with traffic protection";
          }
        }
        default "OFF";
        description
          "Trace Fail Mode";
        config true;
      }
      leaf trc {
        yang:create-supported "true";
        yang:get-supported "true";
        yang:edit-supported "true";
        yang:delete-supported "false";
        type string {
          length "1..48";
        }
        description
          "Outgoing Trace Message";
        config true;
      }
      leaf exp-trc {
        yang:create-supported "true";
        yang:get-supported "true";
        yang:edit-supported "true";
        yang:delete-supported "false";
        type string {
          length "1..48";
        }
        description
          "Expected Trace Message";
        config true;
      }
      leaf clfi {
        yang:create-supported "true";
        yang:get-supported "true";
        yang:edit-supported "true";
        yang:delete-supported "false";
        type ciena-6500-types:STRING;
        description
          "Common Language Facility Identifier.Customer provisionable label for a facility.";
        config true;
      }
      leaf ing-police {
        yang:create-supported "true";
        yang:get-supported "true";
        yang:edit-supported "true";
        yang:delete-supported "false";
        type enumeration {
          enum ENABLED {
            description
              "Enable Ingress Policing";
          }
          enum DISABLED {
            description
              "Disable Ingress Policing";
          }
        }
        default "DISABLED";
        description
          "Ingress Policing. Only supported on the OTN FlexMOTR.";
        config true;
      }
      leaf cir {
        default "1";
        yang:create-supported "true";
        yang:get-supported "true";
        yang:edit-supported "true";
        yang:delete-supported "false";
        type ciena-6500-types:INT {
          range "1..1000000";
        }
        description
          "Committed Information Rate. Measured in kb/s.";
        config true;
      }
      leaf cbs {
        default "12176";
        yang:create-supported "true";
        yang:get-supported "true";
        yang:edit-supported "true";
        yang:delete-supported "false";
        type ciena-6500-types:INT {
          range "1..131071";
        }
        description
          "Committed Burst Size";
        config true;
      }
      leaf cbs-units {
        yang:create-supported "true";
        yang:get-supported "true";
        yang:edit-supported "true";
        yang:delete-supported "false";
        type enumeration {
          enum BYTE {
            description
              "Commited Burst Size is measured in Bytes";
          }
          enum KBYTE {
            description
              "Commited Burst Size is measured in KBytes";
          }
        }
        default "BYTE";
        description
          "Committed Burst Size Units. Only supported when CBS is supported. Only supported on the OTN FlexMOTR.";
        config true;
      }
      leaf pst {
        yang:create-supported "true";
        yang:get-supported "true";
        yang:edit-supported "false";
        yang:delete-supported "false";
        type enumeration {
          enum IS {
            description
              "In Service(This value can be used in create operation)";
          }
          enum OOS-MA {
            description
              "Out-of-service maintenance for provisioning manual administration(This value can be used in create operation)";
          }
          enum IS-ANR {
            description
              "In Service - Abnormal";
          }
          enum OOS-AU {
            description
              "Out-of-service autonomous from a failure detected point of view. It is not out of service from a state point of view. Alarm is raised if the entity is not able to perform its provisioned functions";
          }
          enum OOS-AUMA {
            description
              "Out-of-service autonomous management - the entity is not able to perform its provisioned functions and is purposefully removed from service";
          }
          enum OOS-MAANR {
            description
              "Out-of-service maintenance - abnormal";
          }
        }
        description
          "Identify the primary state";
        config true;
      }
      leaf-list sst {
        yang:create-supported "true";
        yang:get-supported "true";
        yang:edit-supported "true";
        yang:delete-supported "false";
        type enumeration {
          enum AINS {
            description
              "Auto-In-Service(This value can be used in create and edit operations)";
          }
          enum AINS-DEA {
            description
              "Auto-In-Service Deactivate(This value can be used in create and edit operations)";
          }
          enum MT {
            description
              "Maintenance(This value can be used in create operation)";
          }
          enum FLT {
            description
              "Fault detected in equipment";
          }
          enum LPBK {
            description
              "Loopback";
          }
          enum SGEO {
            description
              "Supporting entity outage";
          }
          enum DISCD {
            description
              "Disconnected. (no transparent traffic connection on this facility)";
          }
          enum TSGEN {
            description
              "Test set generation";
          }
          enum TSMON {
            description
              "Test set monitor";
          }
        }
        description
          "Identify the secondary state.";
        config true;
      }
      leaf mappedrate {
        yang:create-supported "false";
        yang:get-supported "true";
        yang:edit-supported "false";
        yang:delete-supported "false";
        type ciena-6500-types:INT;
        description
          "Mapped Rate, in Mbps";
        config false;
      }
      leaf defrag-hit {
        yang:create-supported "false";
        yang:get-supported "true";
        yang:edit-supported "false";
        yang:delete-supported "false";
        type enumeration {
          enum YES {
            description
              "Traffic is impacted on this port";
          }
          enum NO {
            description
              "No Traffic impact on this port";
          }
        }
        description
          "Determine if this port will be impacted by Bandwidth Defragmenation";
        config false;
      }
      leaf tx-act-pwr {
        yang:create-supported "false";
        yang:get-supported "true";
        yang:edit-supported "false";
        yang:delete-supported "false";
        type ciena-6500-types:STRING;
        description
          "TX actual power in dBm (xx.x)";
        config false;
      }
      leaf tx-min-pwr {
        yang:create-supported "false";
        yang:get-supported "true";
        yang:edit-supported "false";
        yang:delete-supported "false";
        type ciena-6500-types:STRING;
        description
          "TX minimum power in dBm (xx.x)";
        config false;
      }
      leaf tx-max-pwr {
        yang:create-supported "false";
        yang:get-supported "true";
        yang:edit-supported "false";
        yang:delete-supported "false";
        type ciena-6500-types:STRING;
        description
          "TX maximum power in dBm (xx.x)";
        config false;
      }
      leaf rx-act-pwr {
        yang:create-supported "false";
        yang:get-supported "true";
        yang:edit-supported "false";
        yang:delete-supported "false";
        type ciena-6500-types:STRING;
        description
          "RX actual power in dBm (xx.x)";
        config false;
      }
      leaf rx-min-pwr {
        yang:create-supported "false";
        yang:get-supported "true";
        yang:edit-supported "false";
        yang:delete-supported "false";
        type ciena-6500-types:STRING;
        description
          "RX minimum power in dBm (xx.x)";
        config false;
      }
      leaf rx-max-pwr {
        yang:create-supported "false";
        yang:get-supported "true";
        yang:edit-supported "false";
        yang:delete-supported "false";
        type ciena-6500-types:STRING;
        description
          "RX maximum power in dBm (xx.x)";
        config false;
      }
      leaf ains-time-left {
        yang:create-supported "false";
        yang:get-supported "true";
        yang:edit-supported "false";
        yang:delete-supported "false";
        type ciena-6500-types:TIME;
        description
          "The format will be HH-MM for the time left in AINS timeout.";
        config false;
      }
      leaf prime {
        yang:create-supported "false";
        yang:get-supported "true";
        yang:edit-supported "false";
        yang:delete-supported "false";
        type ciena-6500-types:STRING;
        description
          "The AID of the prime (ETH40G-shelf-slot-port).";
        config false;
      }
      leaf defrag {
        yang:create-supported "false";
        yang:get-supported "false";
        yang:edit-supported "true";
        yang:delete-supported "false";
        type enumeration {
          enum YES {
            description
              "Allow internal Bandwidth Re-allocations / Defragmentation";
          }
          enum NO {
            description
              "No Effect";
          }
        }
        description
          "Allow internal Bandwidth Re-allocations / Defragmentation";
        config true;
      }
    }
    list oc3 {
      yang:handler "tl1";
      yang:create-supported "false";
      yang:get-supported "true";
      yang:edit-supported "true";
      yang:delete-supported "false";
      key "oc3";
      config true;
      leaf oc3 {
        mandatory true;
        description
          "AID in format OC3-shelf-slot-port, ALL";
        type ciena-6500-types:aid;
      }
      leaf sd-th {
        default "6";
        yang:get-supported "true";
        yang:edit-supported "true";
        type ciena-6500-types:INT {
          range "5..9";
        }
        description
          "Signal degrade threshold value";
        config true;
      }
      leaf stformat {
        yang:get-supported "true";
        yang:edit-supported "true";
        type enumeration {
          enum NUM {
            description
              "1 byte";
          }
          enum STRING {
            description
              "16 byte";
          }
        }
        description
          "Section Trace Format";
        config true;
      }
      leaf strc {
        yang:get-supported "true";
        yang:edit-supported "true";
        type ciena-6500-types:STRING;
        description
          "Transmitted section trace";
        config true;
      }
      leaf exp-trc {
        yang:get-supported "true";
        yang:edit-supported "true";
        type ciena-6500-types:STRING;
        description
          "Expected section trace";
        config true;
      }
      leaf stfmode {
        yang:get-supported "true";
        yang:edit-supported "true";
        type enumeration {
          enum OFF {
            description
              "Alarms off, no traffic protection";
          }
          enum ALMONLY {
            description
              "Alarms on, no traffic protection";
          }
          enum LINEFAIL {
            description
              "Alarms on, with traffic protection";
          }
        }
        default "OFF";
        description
          "Section Trace Fail Mode";
        config true;
      }
      leaf als {
        yang:get-supported "true";
        yang:edit-supported "true";
        type enumeration {
          enum ENABLED;
          enum DISABLED;
        }
        default "ENABLED";
        description
          "Automatic Laser Shutdown";
        config true;
      }
      leaf eber-thresh {
        default "3";
        yang:get-supported "true";
        yang:edit-supported "true";
        type ciena-6500-types:INT {
          range "3 | 4 | 5";
        }
        description
          "Excessive bit error threshold value";
        config true;
      }
      leaf ssbitmde {
        yang:get-supported "true";
        yang:edit-supported "true";
        type ciena-6500-enums:SSBITMDE;
        description
          "SS Bit mode (facility personality)";
        config true;
      }
      leaf dus-override {
        yang:get-supported "true";
        yang:edit-supported "true";
        type enumeration {
          enum ENABLED;
          enum DISABLED;
        }
        description
          "A parameter which allows the synchronization quality level of a line reference to be overriden even when the receiving quality level is DUS.";
        config true;
      }
      leaf uneqmode {
        yang:get-supported "true";
        yang:edit-supported "true";
        type enumeration {
          enum UNKNOWN {
            description
              "Unknown unequipped insertion mode";
          }
          enum STS1 {
            description
              "Insert STS1 Unequipped";
          }
          enum VC4 {
            description
              "Insert VC4 Unequipped";
          }
        }
        description
          "Unequipped Insertion Mode";
        config true;
      }
      leaf clfi {
        yang:get-supported "true";
        yang:edit-supported "true";
        type ciena-6500-types:STRING;
        description
          "Common Language Facility Identifier.Customer provisionable label for a facility.";
        config true;
      }
      leaf-list sst {
        yang:get-supported "true";
        yang:edit-supported "true";
        type enumeration {
          enum AINS {
            description
              "Auto-In-Service(This value can be used in edit operation)";
          }
          enum AINS-DEA {
            description
              "Auto-In-Service Deactivate(This value can be used in edit operation)";
          }
          enum TS {
            description
              "Test Access(This value can be used in edit operation)";
          }
          enum TS-DEA {
            description
              "Test Access Deactivate(This value can be used in edit operation)";
          }
          enum MT {
            description
              "Maintenance";
          }
          enum DISCD {
            description
              "Disconnected (no cross-connects exist on facility)";
          }
          enum LPBK {
            description
              "Loopback";
          }
          enum FLT {
            description
              "Fault detected in equipment";
          }
          enum SGEO {
            description
              "Supporting entity outage";
          }
          enum WRKRX {
            description
              "Working in the receive direction";
          }
          enum WRKTX {
            description
              "Working in the transmit direction";
          }
        }
        description
          "Identify the secondary state's auto-in-service/Test Access state";
        config true;
      }
      leaf timing-reference {
        yang:get-supported "true";
        yang:edit-supported "false";
        type ciena-6500-enums:BOOL_Y_N;
        description
          "Facility is a Timing Reference.";
        config false;
      }
      leaf dcc {
        yang:get-supported "true";
        yang:edit-supported "false";
        type ciena-6500-enums:BOOL_Y_N;
        description
          "Facility has DCC enabled";
        config false;
      }
      leaf port-mode {
        yang:get-supported "true";
        yang:edit-supported "false";
        type enumeration {
          enum SONET;
          enum SDH;
        }
        description
          "Optical Port market preference";
        config false;
      }
      leaf ains-time-left {
        yang:get-supported "true";
        yang:edit-supported "false";
        type ciena-6500-types:TIME;
        description
          "The format will be \"HH-MM\" for the time left in AINS timeout.";
        config false;
      }
      leaf dsminfo {
        yang:get-supported "true";
        yang:edit-supported "false";
        type enumeration {
          enum YES;
          enum NO;
          enum NONE {
            description
              "Not a DSM provisioned link";
          }
          enum HOSTSIDE {
            description
              "Host located intermediate line facility";
          }
          enum DSMSIDE {
            description
              "DSM located intermediate line facility";
          }
        }
        description
          "Specify if the DSM information is to be included in the response.";
        config false;
      }
      leaf pst {
        yang:get-supported "true";
        yang:edit-supported "false";
        type enumeration {
          enum IS {
            description
              "In Service";
          }
          enum IS-ANR {
            description
              "In Service - Abnormal";
          }
          enum OOS-MA {
            description
              "Out-of-service maintenance for provisioning memory administration";
          }
          enum OOS-AU {
            description
              "Out-of-service autonomous from a failure detected point of view. It is not out of service from a state point of view. Alarm is raised if the entity is not able to perform its provisioned functions";
          }
          enum OOS-AUMA {
            description
              "Out-of-service autonomous management - the entity is not able to perform its provisioned functions and is purposefully removed from service";
          }
          enum OOS-MAANR {
            description
              "Out-of-service maintenance - abnormal.";
          }
        }
        description
          "Identify the primary state";
        config false;
      }
    }
    list oc12 {
      yang:handler "tl1";
      yang:create-supported "false";
      yang:get-supported "true";
      yang:edit-supported "true";
      yang:delete-supported "false";
      key "oc12";
      config true;
      leaf oc12 {
        mandatory true;
        description
          "AID in format OC12-shelf-slot-port, ALL";
        type ciena-6500-types:aid;
      }
      leaf sd-th {
        default "6";
        yang:get-supported "true";
        yang:edit-supported "true";
        type ciena-6500-types:INT {
          range "5..9";
        }
        description
          "Signal degrade threshold value";
        config true;
      }
      leaf stformat {
        yang:get-supported "true";
        yang:edit-supported "true";
        type enumeration {
          enum NUM {
            description
              "1 byte";
          }
          enum STRING {
            description
              "16 byte";
          }
        }
        description
          "Section Trace Format";
        config true;
      }
      leaf strc {
        yang:get-supported "true";
        yang:edit-supported "true";
        type ciena-6500-types:STRING;
        description
          "Transmitted section trace";
        config true;
      }
      leaf exp-trc {
        yang:get-supported "true";
        yang:edit-supported "true";
        type ciena-6500-types:STRING;
        description
          "Expected section trace";
        config true;
      }
      leaf stfmode {
        yang:get-supported "true";
        yang:edit-supported "true";
        type enumeration {
          enum OFF {
            description
              "Alarms off, no traffic protection";
          }
          enum ALMONLY {
            description
              "Alarms on, no traffic protection";
          }
          enum LINEFAIL {
            description
              "Alarms on, with traffic protection";
          }
        }
        default "OFF";
        description
          "Section Trace Fail Mode";
        config true;
      }
      leaf als {
        yang:get-supported "true";
        yang:edit-supported "true";
        type enumeration {
          enum ENABLED;
          enum DISABLED;
        }
        default "ENABLED";
        description
          "Automatic Laser Shutdown";
        config true;
      }
      leaf eber-thresh {
        default "3";
        yang:get-supported "true";
        yang:edit-supported "true";
        type ciena-6500-types:INT {
          range "3 | 4 | 5";
        }
        description
          "Excessive bit error threshold value";
        config true;
      }
      leaf ssbitmde {
        yang:get-supported "true";
        yang:edit-supported "true";
        type ciena-6500-enums:SSBITMDE;
        description
          "SS Bit mode (facility personality)";
        config true;
      }
      leaf dus-override {
        yang:get-supported "true";
        yang:edit-supported "true";
        type enumeration {
          enum ENABLED;
          enum DISABLED;
        }
        description
          "A parameter which allows the synchronization quality level of a line reference to be overriden even when the receiving quality level is DUS";
        config true;
      }
      leaf uneqmode {
        yang:get-supported "true";
        yang:edit-supported "true";
        type enumeration {
          enum UNKNOWN {
            description
              "Unknown unequipped insertion mode";
          }
          enum STS1 {
            description
              "Insert STS1 Unequipped";
          }
          enum VC4 {
            description
              "Insert VC4 Unequipped";
          }
        }
        description
          "Unequipped Insertion Mode";
        config true;
      }
      leaf clfi {
        yang:get-supported "true";
        yang:edit-supported "true";
        type ciena-6500-types:STRING;
        description
          "Common Language Facility Identifier.Customer provisionable label for a facility.";
        config true;
      }
      leaf-list sst {
        yang:get-supported "true";
        yang:edit-supported "true";
        type enumeration {
          enum AINS {
            description
              "Auto-In-Service(This value can be used in edit operation)";
          }
          enum AINS-DEA {
            description
              "Auto-In-Service Deactivate(This value can be used in edit operation)";
          }
          enum TS {
            description
              "Test Access(This value can be used in edit operation)";
          }
          enum TS-DEA {
            description
              "Test Access Deactivate(This value can be used in edit operation)";
          }
          enum MT {
            description
              "Maintenance";
          }
          enum DISCD {
            description
              "Disconnected (no cross-connects exist on facility)";
          }
          enum LPBK {
            description
              "Loopback";
          }
          enum FLT {
            description
              "Fault detected in equipment";
          }
          enum SGEO {
            description
              "Supporting entity outage";
          }
          enum WRKRX {
            description
              "Working in the receive direction";
          }
          enum WRKTX {
            description
              "Working in the transmit direction";
          }
        }
        description
          "Identify the secondary state's auto-in-service/Test Access state";
        config true;
      }
      leaf timing-reference {
        yang:get-supported "true";
        yang:edit-supported "false";
        type ciena-6500-enums:BOOL_Y_N;
        description
          "Facility is a Timing Reference.";
        config false;
      }
      leaf dcc {
        yang:get-supported "true";
        yang:edit-supported "false";
        type ciena-6500-enums:BOOL_Y_N;
        description
          "Facility has DCC enabled";
        config false;
      }
      leaf port-mode {
        yang:get-supported "true";
        yang:edit-supported "false";
        type enumeration {
          enum SONET;
          enum SDH;
        }
        description
          "Optical Port market preference";
        config false;
      }
      leaf ains-time-left {
        yang:get-supported "true";
        yang:edit-supported "false";
        type ciena-6500-types:TIME;
        description
          "The format will be \"HH-MM\" for the time left in AINS timeout.";
        config false;
      }
      leaf pst {
        yang:get-supported "true";
        yang:edit-supported "false";
        type enumeration {
          enum IS {
            description
              "In Service";
          }
          enum IS-ANR {
            description
              "In Service - Abnormal";
          }
          enum OOS-MA {
            description
              "Out-of-service maintenance for provisioning memory administration";
          }
          enum OOS-AU {
            description
              "Out-of-service autonomous from a failure detected point of view. It is not out of service from a state point of view. Alarm is raised if the entity is not able to perform its provisioned functions";
          }
          enum OOS-AUMA {
            description
              "Out-of-service autonomous management - the entity is not able to perform its provisioned functions and is purposefully removed from service";
          }
          enum OOS-MAANR {
            description
              "Out-of-service maintenance - abnormal.";
          }
        }
        description
          "Identify the primary state";
        config false;
      }
    }
    list oc48 {
      yang:handler "tl1";
      yang:create-supported "false";
      yang:get-supported "true";
      yang:edit-supported "true";
      yang:delete-supported "false";
      key "oc48";
      config true;
      leaf oc48 {
        mandatory true;
        description
          "AID in format OC48-shelf-slot-port, ALL";
        type ciena-6500-types:aid;
      }
      leaf sd-th {
        default "6";
        yang:get-supported "true";
        yang:edit-supported "true";
        type ciena-6500-types:INT {
          range "5..9";
        }
        description
          "Signal degrade threshold value";
        config true;
      }
      leaf stformat {
        yang:get-supported "true";
        yang:edit-supported "true";
        type enumeration {
          enum NUM {
            description
              "1 byte";
          }
          enum STRING {
            description
              "16 byte";
          }
        }
        description
          "Section Trace Format";
        config true;
      }
      leaf strc {
        yang:get-supported "true";
        yang:edit-supported "true";
        type ciena-6500-types:STRING;
        description
          "Transmitted section trace";
        config true;
      }
      leaf exp-trc {
        yang:get-supported "true";
        yang:edit-supported "true";
        type ciena-6500-types:STRING;
        description
          "Expected section trace";
        config true;
      }
      leaf stfmode {
        yang:get-supported "true";
        yang:edit-supported "true";
        type enumeration {
          enum OFF {
            description
              "Alarms off, no traffic protection";
          }
          enum ALMONLY {
            description
              "Alarms on, no traffic protection";
          }
          enum LINEFAIL {
            description
              "Alarms on, traffic protection (OC48 facilities only)";
          }
        }
        default "OFF";
        description
          "Section Trace Fail Mode";
        config true;
      }
      leaf als {
        yang:get-supported "true";
        yang:edit-supported "true";
        type enumeration {
          enum ENABLED;
          enum DISABLED;
        }
        default "ENABLED";
        description
          "Automatic Laser Shutdown";
        config true;
      }
      leaf ssbitmde {
        yang:get-supported "true";
        yang:edit-supported "true";
        type ciena-6500-enums:SSBITMDE;
        description
          "SS Bit mode (facility personality)";
        config true;
      }
      leaf eber-thresh {
        default "3";
        yang:get-supported "true";
        yang:edit-supported "true";
        type ciena-6500-types:INT {
          range "3 | 4 | 5";
        }
        description
          "Excessive bit error threshold value";
        config true;
      }
      leaf dus-override {
        yang:get-supported "true";
        yang:edit-supported "true";
        type enumeration {
          enum ENABLED;
          enum DISABLED;
        }
        description
          "A parameter which allows the synchronization quality level of a line reference to be overriden even when the receiving quality level is DUS";
        config true;
      }
      leaf uneqmode {
        yang:get-supported "true";
        yang:edit-supported "true";
        type enumeration {
          enum UNKNOWN {
            description
              "Unknown unequipped insertion mode";
          }
          enum STS1 {
            description
              "Insert STS1 Unequipped";
          }
          enum VC4 {
            description
              "Insert VC4 Unequipped";
          }
        }
        description
          "Unequipped Insertion Mode";
        config true;
      }
      leaf clfi {
        yang:get-supported "true";
        yang:edit-supported "true";
        type ciena-6500-types:STRING;
        description
          "Common Language Facility Identifier.Customer provisionable label for a facility.";
        config true;
      }
      leaf rout-sig-disabled {
        yang:get-supported "true";
        yang:edit-supported "true";
        type enumeration {
          enum NO {
            description
              "Used by control plane";
          }
          enum YES {
            description
              "Not used by control plane";
          }
        }
        default "YES";
        description
          "This attribute controls whether the underlying interface will be used by control plane for I-NNI routing and signaling purposes.";
        config true;
      }
      leaf-list sst {
        yang:get-supported "true";
        yang:edit-supported "true";
        type enumeration {
          enum AINS {
            description
              "Auto-In-Service(This value can be used in edit operation)";
          }
          enum AINS-DEA {
            description
              "Auto-In-Service Deactivate(This value can be used in edit operation)";
          }
          enum MT {
            description
              "Maintenance";
          }
          enum DISCD {
            description
              "Disconnected (no cross-connects exist on facility)";
          }
          enum LPBK {
            description
              "Loopback";
          }
          enum FLT {
            description
              "Fault detected in equipment";
          }
          enum TS {
            description
              "Test";
          }
          enum SGEO {
            description
              "Supporting entity outage";
          }
          enum WRKRX {
            description
              "Working in the receive direction";
          }
          enum WRKTX {
            description
              "Working in the transmit direction";
          }
        }
        description
          "Identify the secondary state's auto-in-service state";
        config true;
      }
      leaf timing-reference {
        yang:get-supported "true";
        yang:edit-supported "false";
        type ciena-6500-enums:BOOL_Y_N;
        description
          "Facility is a Timing Reference.";
        config false;
      }
      leaf dcc {
        yang:get-supported "true";
        yang:edit-supported "false";
        type ciena-6500-enums:BOOL_Y_N;
        description
          "Facility has DCC enabled";
        config false;
      }
      leaf port-mode {
        yang:get-supported "true";
        yang:edit-supported "false";
        type enumeration {
          enum SONET;
          enum SDH;
        }
        description
          "Optical Port market preference";
        config false;
      }
      leaf ains-time-left {
        yang:get-supported "true";
        yang:edit-supported "false";
        type ciena-6500-types:TIME;
        description
          "The format will be \"HH-MM\" for the time left in AINS timeout.";
        config false;
      }
      leaf och-rx-act-power {
        yang:get-supported "true";
        yang:edit-supported "false";
        type ciena-6500-types:STRING;
        description
          "RX actual power in dBm (xx.x)";
        config false;
      }
      leaf och-tx-act-power {
        yang:get-supported "true";
        yang:edit-supported "false";
        type ciena-6500-types:STRING;
        description
          "TX actual power in dBm (xx.x)";
        config false;
      }
      leaf och-rx-min-power {
        yang:get-supported "true";
        yang:edit-supported "false";
        type ciena-6500-types:STRING;
        description
          "RX minimum power in dBm (xx.x)";
        config false;
      }
      leaf och-rx-max-power {
        yang:get-supported "true";
        yang:edit-supported "false";
        type ciena-6500-types:STRING;
        description
          "RX maximum power in dBm (xx.x)";
        config false;
      }
      leaf och-tx-min-power {
        yang:get-supported "true";
        yang:edit-supported "false";
        type ciena-6500-types:STRING;
        description
          "TX minimum power in dBm (xx.x)";
        config false;
      }
      leaf och-tx-max-power {
        yang:get-supported "true";
        yang:edit-supported "false";
        type ciena-6500-types:STRING;
        description
          "TX maximum power in dBm (xx.x)";
        config false;
      }
      leaf pst {
        yang:get-supported "true";
        yang:edit-supported "false";
        type enumeration {
          enum IS {
            description
              "In Service";
          }
          enum IS-ANR {
            description
              "In Service - Abnormal";
          }
          enum OOS-MA {
            description
              "Out-of-service maintenance for provisioning memory administration";
          }
          enum OOS-AU {
            description
              "Out-of-service autonomous from a failure detected point of view. It is not out of service from a state point of view. Alarm is raised if the entity is not able to perform its provisioned functions";
          }
          enum OOS-AUMA {
            description
              "Out-of-service autonomous management - the entity is not able to perform its provisioned functions and is purposefully removed from service";
          }
          enum OOS-MAANR {
            description
              "Out-of-service maintenance - abnormal.";
          }
        }
        description
          "Identify the primary state";
        config false;
      }
      leaf laserofffarendfail {
        yang:get-supported "false";
        yang:edit-supported "true";
        type ciena-6500-enums:Laserofffarendfail;
        default "DISABLED";
        description
          "Loss of light feature";
        config true;
      }
    }
    list oc192 {
      yang:handler "tl1";
      yang:create-supported "true";
      yang:get-supported "true";
      yang:edit-supported "true";
      yang:delete-supported "true";
      key "oc192";
      config true;
      leaf oc192 {
        mandatory true;
        description
          "AID in format OC192-shelf-slot-port, OC192-shelf-slot-portSsubport, ALL";
        type ciena-6500-types:aid;
      }
      leaf sd-th {
        default "6";
        yang:create-supported "true";
        yang:get-supported "true";
        yang:edit-supported "true";
        yang:delete-supported "false";
        type ciena-6500-types:INT {
          range "5..9";
        }
        description
          "Signal degrade threshold value";
        config true;
      }
      leaf stformat {
        yang:create-supported "true";
        yang:get-supported "true";
        yang:edit-supported "true";
        yang:delete-supported "false";
        type enumeration {
          enum NUM {
            description
              "1 byte";
          }
          enum STRING {
            description
              "16 byte";
          }
        }
        description
          "Section Trace Format";
        config true;
      }
      leaf strc {
        yang:create-supported "true";
        yang:get-supported "true";
        yang:edit-supported "true";
        yang:delete-supported "false";
        type ciena-6500-types:STRING;
        description
          "Transmitted section trace";
        config true;
      }
      leaf exp-trc {
        yang:create-supported "true";
        yang:get-supported "true";
        yang:edit-supported "true";
        yang:delete-supported "false";
        type ciena-6500-types:STRING;
        description
          "Expected section trace";
        config true;
      }
      leaf stfmode {
        yang:create-supported "true";
        yang:get-supported "true";
        yang:edit-supported "true";
        yang:delete-supported "false";
        type enumeration {
          enum OFF {
            description
              "Alarms off, no traffic protection";
          }
          enum ALMONLY {
            description
              "Alarms on, no traffic protection";
          }
          enum LINEFAIL {
            description
              "Alarms on, with traffic protection";
          }
        }
        default "OFF";
        description
          "Section Trace Fail Mode";
        config true;
      }
      leaf als {
        yang:create-supported "true";
        yang:get-supported "true";
        yang:edit-supported "true";
        yang:delete-supported "false";
        type enumeration {
          enum ENABLED;
          enum DISABLED;
        }
        default "ENABLED";
        description
          "Automatic Laser Shutdown";
        config true;
      }
      leaf ssbitmde {
        yang:create-supported "true";
        yang:get-supported "true";
        yang:edit-supported "true";
        yang:delete-supported "false";
        type enumeration {
          enum SONET;
          enum SDH;
        }
        description
          "SS Bit mode (facility personality)";
        config true;
      }
      leaf fec {
        yang:create-supported "true";
        yang:get-supported "true";
        yang:edit-supported "true";
        yang:delete-supported "false";
        type ciena-6500-enums:FEC;
        default "RS8";
        description
          "FEC";
        config true;
      }
      leaf nls {
        yang:create-supported "true";
        yang:get-supported "true";
        yang:edit-supported "true";
        yang:delete-supported "false";
        type ciena-6500-enums:BOOL_ON_OFF;
        description
          "Non Linear Supression compensation";
        config true;
      }
      leaf eber-thresh {
        default "3";
        yang:create-supported "true";
        yang:get-supported "true";
        yang:edit-supported "true";
        yang:delete-supported "false";
        type ciena-6500-types:INT {
          range "3 | 4 | 5";
        }
        description
          "Excessive bit error threshold value";
        config true;
      }
      leaf laserofffarendfail {
        yang:create-supported "true";
        yang:get-supported "true";
        yang:edit-supported "true";
        yang:delete-supported "false";
        type ciena-6500-enums:Laserofffarendfail;
        default "DISABLED";
        description
          "Loss of light feature";
        config true;
      }
      leaf port-mode {
        yang:create-supported "true";
        yang:get-supported "true";
        yang:edit-supported "true";
        yang:delete-supported "false";
        type enumeration {
          enum SONET;
          enum SDH;
        }
        description
          "Optical Port market preference";
        config true;
      }
      leaf dus-override {
        yang:create-supported "true";
        yang:get-supported "true";
        yang:edit-supported "true";
        yang:delete-supported "false";
        type enumeration {
          enum ENABLED;
          enum DISABLED;
        }
        description
          "A parameter which allows the synchronization quality level of a line reference to be overriden even when the receiving quality level is DUS";
        config true;
      }
      leaf uneqmode {
        yang:create-supported "true";
        yang:get-supported "true";
        yang:edit-supported "true";
        yang:delete-supported "false";
        type enumeration {
          enum UNKNOWN {
            description
              "Unknown unequipped insertion mode";
          }
          enum STS1 {
            description
              "Insert STS1 Unequipped";
          }
          enum VC4 {
            description
              "Insert VC4 Unequipped";
          }
        }
        description
          "Unequipped Insertion Mode";
        config true;
      }
      leaf clfi {
        yang:create-supported "true";
        yang:get-supported "true";
        yang:edit-supported "true";
        yang:delete-supported "false";
        type ciena-6500-types:STRING;
        description
          "Common Language Facility Identifier.Customer provisionable label for a facility.";
        config true;
      }
      leaf rout-sig-disabled {
        yang:create-supported "true";
        yang:get-supported "true";
        yang:edit-supported "true";
        yang:delete-supported "false";
        type enumeration {
          enum NO {
            description
              "Used by control plane";
          }
          enum YES {
            description
              "Not used by control plane";
          }
        }
        default "YES";
        description
          "This attribute controls whether the underlying interface will be used by control plane for I-NNI routing and signaling purposes.";
        config true;
      }
      leaf ochtxwvlngthprov {
        yang:create-supported "true";
        yang:get-supported "true";
        yang:edit-supported "true";
        yang:delete-supported "false";
        type ciena-6500-types:STRING;
        description
          "Provisioned Wavelength in nm (xxxx.xx)";
        config true;
      }
      leaf-list sst {
        yang:create-supported "true";
        yang:get-supported "true";
        yang:edit-supported "true";
        yang:delete-supported "false";
        type enumeration {
          enum AINS {
            description
              "Auto-In-Service(This value can be used in create and edit operations)";
          }
          enum AINS-DEA {
            description
              "Auto-In-Service Deactivate(This value can be used in create and edit operations)";
          }
          enum MT {
            description
              "Maintenance(This value can be used in create operation)";
          }
          enum DISCD {
            description
              "Disconnected (no cross-connects exist on facility)";
          }
          enum LPBK {
            description
              "Loopback";
          }
          enum FLT {
            description
              "Fault detected in equipment";
          }
          enum TS {
            description
              "Test";
          }
          enum SGEO {
            description
              "Supporting entity outage";
          }
          enum WRKRX {
            description
              "Working in the receive direction";
          }
          enum WRKTX {
            description
              "Working in the transmit direction";
          }
          enum TSGEN {
            description
              "Test set generation";
          }
          enum TSMON {
            description
              "Test set monitor";
          }
        }
        description
          "Identify the secondary state's auto-in-service state";
        config true;
      }
      leaf mapping {
        yang:create-supported "true";
        yang:get-supported "true";
        yang:edit-supported "false";
        yang:delete-supported "false";
        type enumeration {
          enum NONE {
            description
              "Not Mapped";
          }
          enum AMP {
            description
              "AMP Mapping";
          }
          enum BMP {
            description
              "BMP Mapping";
          }
        }
        description
          "Signal Mapping";
        config true;
      }
      leaf ste {
        yang:create-supported "true";
        yang:get-supported "true";
        yang:edit-supported "false";
        yang:delete-supported "false";
        type enumeration {
          enum YES {
            description
              "Facility is section terminating.";
          }
          enum NO {
            description
              "Facility is section transparent.";
          }
        }
        description
          "Section Terminating";
        config true;
      }
      leaf pst {
        yang:create-supported "true";
        yang:get-supported "true";
        yang:edit-supported "false";
        yang:delete-supported "false";
        type enumeration {
          enum IS {
            description
              "In Service(This value can be used in create operation)";
          }
          enum OOS-MA {
            description
              "Out-of-service maintenance for provisioning memory administration(This value can be used in create operation)";
          }
          enum IS-ANR {
            description
              "In Service - Abnormal";
          }
          enum OOS-AU {
            description
              "Out-of-service autonomous from a failure detected point of view. It is not out of service from a state point of view. Alarm is raised if the entity is not able to perform its provisioned functions";
          }
          enum OOS-AUMA {
            description
              "Out-of-service autonomous management - the entity is not able to perform its provisioned functions and is purposefully removed from service";
          }
          enum OOS-MAANR {
            description
              "Out-of-service maintenance - abnormal.";
          }
        }
        description
          "Identify the primary state";
        config true;
      }
      leaf timing-reference {
        yang:create-supported "false";
        yang:get-supported "true";
        yang:edit-supported "false";
        yang:delete-supported "false";
        type ciena-6500-enums:BOOL_Y_N;
        description
          "Facility is a Timing Reference.";
        config false;
      }
      leaf dcc {
        yang:create-supported "false";
        yang:get-supported "true";
        yang:edit-supported "false";
        yang:delete-supported "false";
        type ciena-6500-enums:BOOL_Y_N;
        description
          "Facility has DCC enabled";
        config false;
      }
      leaf ains-time-left {
        yang:create-supported "false";
        yang:get-supported "true";
        yang:edit-supported "false";
        yang:delete-supported "false";
        type ciena-6500-types:TIME;
        description
          "The format will be \"HH-MM\" for the time left in AINS timeout.";
        config false;
      }
      leaf och-rx-act-power {
        yang:create-supported "false";
        yang:get-supported "true";
        yang:edit-supported "false";
        yang:delete-supported "false";
        type ciena-6500-types:STRING;
        description
          "RX actual power in dBm (xx.x)";
        config false;
      }
      leaf och-rx-min-power {
        yang:create-supported "false";
        yang:get-supported "true";
        yang:edit-supported "false";
        yang:delete-supported "false";
        type ciena-6500-types:STRING;
        description
          "RX minimum power in dBm (xx.x)";
        config false;
      }
      leaf och-rx-max-power {
        yang:create-supported "false";
        yang:get-supported "true";
        yang:edit-supported "false";
        yang:delete-supported "false";
        type ciena-6500-types:STRING;
        description
          "RX maximum power in dBm (xx.x)";
        config false;
      }
      leaf och-tx-act-power {
        yang:create-supported "false";
        yang:get-supported "true";
        yang:edit-supported "false";
        yang:delete-supported "false";
        type ciena-6500-types:STRING;
        description
          "TX actual power in dBm (xx.x)";
        config false;
      }
      leaf och-tx-min-power {
        yang:create-supported "false";
        yang:get-supported "true";
        yang:edit-supported "false";
        yang:delete-supported "false";
        type ciena-6500-types:STRING;
        description
          "TX minimum power in dBm (xx.x)";
        config false;
      }
      leaf och-tx-max-power {
        yang:create-supported "false";
        yang:get-supported "true";
        yang:edit-supported "false";
        yang:delete-supported "false";
        type ciena-6500-types:STRING;
        description
          "TX maximum power in dBm (xx.x)";
        config false;
      }
      leaf ochtxwvlngthmin {
        default "0.00";
        yang:create-supported "false";
        yang:get-supported "true";
        yang:edit-supported "false";
        yang:delete-supported "false";
        type ciena-6500-types:STRING;
        description
          "Minimum Wavelength value in nm (xxxx.xx)";
        config false;
      }
      leaf ochtxwvlngthmax {
        default "0.00";
        yang:create-supported "false";
        yang:get-supported "true";
        yang:edit-supported "false";
        yang:delete-supported "false";
        type ciena-6500-types:STRING;
        description
          "Maximum Wavelength value in nm (xxxx.xx)";
        config false;
      }
      leaf ochtxwvlngthspacing {
        yang:create-supported "false";
        yang:get-supported "true";
        yang:edit-supported "false";
        yang:delete-supported "false";
        type ciena-6500-types:STRING;
        description
          "OCH Wavelength Spacing in Ghz";
        config false;
      }
      leaf splimgmt {
        yang:create-supported "false";
        yang:get-supported "true";
        yang:edit-supported "false";
        yang:delete-supported "false";
        type ciena-6500-enums:spliMgmt;
        description
          "Identify if Port is Manageable by SPLI";
        config false;
      }
      leaf splimanaged {
        yang:create-supported "false";
        yang:get-supported "true";
        yang:edit-supported "false";
        yang:delete-supported "false";
        type ciena-6500-enums:spliManaged;
        description
          "Identify if Port is Currently Managed by SPLI";
        config false;
      }
      leaf sf-th {
        default "4";
        yang:create-supported "false";
        yang:get-supported "true";
        yang:edit-supported "false";
        yang:delete-supported "false";
        type ciena-6500-types:INT {
          range "4..8";
        }
        description
          "Signal Fail Threshold value";
        config false;
      }
    }
    list oc768 {
      yang:handler "tl1";
      yang:create-supported "true";
      yang:get-supported "true";
      yang:edit-supported "true";
      yang:delete-supported "true";
      key "oc768";
      config true;
      leaf oc768 {
        mandatory true;
        description
          "AID in format OC768-shelf-slot-port, ALL";
        type ciena-6500-types:aid;
      }
      leaf stformat {
        yang:create-supported "true";
        yang:get-supported "true";
        yang:edit-supported "true";
        yang:delete-supported "false";
        type enumeration {
          enum NUM {
            description
              "1 byte";
          }
          enum STRING {
            description
              "16 byte";
          }
        }
        description
          "Section Trace Format";
        config true;
      }
      leaf exp-trc {
        yang:create-supported "true";
        yang:get-supported "true";
        yang:edit-supported "true";
        yang:delete-supported "false";
        type ciena-6500-types:STRING;
        description
          "Expected section trace";
        config true;
      }
      leaf stfmode {
        yang:create-supported "true";
        yang:get-supported "true";
        yang:edit-supported "true";
        yang:delete-supported "false";
        type enumeration {
          enum OFF {
            description
              "Alarms off, no traffic protection";
          }
          enum ALMONLY {
            description
              "Alarms on, no traffic protection";
          }
        }
        default "OFF";
        description
          "Section Trace Fail Mode";
        config true;
      }
      leaf strc {
        yang:create-supported "true";
        yang:get-supported "true";
        yang:edit-supported "true";
        yang:delete-supported "false";
        type ciena-6500-types:STRING;
        description
          "Transmitted section trace";
        config true;
      }
      leaf eber-thresh {
        default "3";
        yang:create-supported "true";
        yang:get-supported "true";
        yang:edit-supported "true";
        yang:delete-supported "false";
        type ciena-6500-types:INT {
          range "3 | 4 | 5";
        }
        description
          "Excessive bit error threshold value";
        config true;
      }
      leaf laserofffarendfail {
        yang:create-supported "true";
        yang:get-supported "true";
        yang:edit-supported "true";
        yang:delete-supported "false";
        type ciena-6500-enums:Laserofffarendfail;
        default "DISABLED";
        description
          "Loss of light feature. Under certain failure scenarios insert Loss of Light (i.e. turn off the TX laser).";
        config true;
      }
      leaf clfi {
        yang:create-supported "true";
        yang:get-supported "true";
        yang:edit-supported "true";
        yang:delete-supported "false";
        type ciena-6500-types:STRING;
        description
          "Common Language Facility Identifier.Customer provisionable label for a facility.";
        config true;
      }
      leaf hold-off {
        default "0";
        yang:create-supported "true";
        yang:get-supported "true";
        yang:edit-supported "true";
        yang:delete-supported "false";
        type ciena-6500-types:INT {
          range "0 | 100 | 200 | 300 | 400 | 500 | 600 | 700 | 800 | 900 | 1000";
        }
        description
          "HoldOff signal conditioning timer";
        config true;
      }
      leaf-list sst {
        yang:create-supported "true";
        yang:get-supported "true";
        yang:edit-supported "true";
        yang:delete-supported "false";
        type enumeration {
          enum AINS {
            description
              "Auto-In-Service(This value can be used in create and edit operations)";
          }
          enum AINS-DEA {
            description
              "Auto-In-Service Deactivate(This value can be used in create and edit operations)";
          }
          enum MT {
            description
              "Maintenance(This value can be used in create operation)";
          }
          enum DISCD {
            description
              "Disconnected (no cross-connects exist on facility)";
          }
          enum LPBK {
            description
              "Loopback";
          }
          enum FLT {
            description
              "Fault detected in equipment";
          }
          enum SGEO {
            description
              "Supporting entity outage";
          }
          enum TSGEN {
            description
              "Test set generation";
          }
          enum TSMON {
            description
              "Test set monitor";
          }
        }
        description
          "Identify the secondary state's auto-in-service state";
        config true;
      }
      leaf port-mode {
        yang:create-supported "true";
        yang:get-supported "true";
        yang:edit-supported "false";
        yang:delete-supported "false";
        type enumeration {
          enum SONET;
          enum SDH;
        }
        description
          "Optical Port market preference";
        config true;
      }
      leaf pst {
        yang:create-supported "true";
        yang:get-supported "true";
        yang:edit-supported "false";
        yang:delete-supported "false";
        type enumeration {
          enum IS {
            description
              "In Service(This value can be used in create operation)";
          }
          enum OOS-MA {
            description
              "Out-of-service maintenance for provisioning memory administration(This value can be used in create operation)";
          }
          enum IS-ANR {
            description
              "In Service - Abnormal";
          }
          enum OOS-AU {
            description
              "Out-of-service autonomous from a failure detected point of view. It is not out of service from a state point of view. Alarm is raised if the entity is not able to perform its provisioned functions";
          }
          enum OOS-AUMA {
            description
              "Out-of-service autonomous management - the entity is not able to perform its provisioned functions and is purposefully removed from service";
          }
          enum OOS-MAANR {
            description
              "Out-of-service maintenance - abnormal.";
          }
        }
        description
          "Identify the primary state";
        config true;
      }
      leaf ains-time-left {
        yang:create-supported "false";
        yang:get-supported "true";
        yang:edit-supported "false";
        yang:delete-supported "false";
        type ciena-6500-types:TIME;
        description
          "The format will be \"HH-MM\" for the time left in AINS timeout.";
        config false;
      }
      leaf och-rx-act-power {
        yang:create-supported "false";
        yang:get-supported "true";
        yang:edit-supported "false";
        yang:delete-supported "false";
        type ciena-6500-types:STRING;
        description
          "RX actual power in dBm (xx.x)";
        config false;
      }
      leaf och-rx-min-power {
        yang:create-supported "false";
        yang:get-supported "true";
        yang:edit-supported "false";
        yang:delete-supported "false";
        type ciena-6500-types:STRING;
        description
          "RX minimum power in dBm (xx.x)";
        config false;
      }
      leaf och-rx-max-power {
        yang:create-supported "false";
        yang:get-supported "true";
        yang:edit-supported "false";
        yang:delete-supported "false";
        type ciena-6500-types:STRING;
        description
          "RX maximum power in dBm (xx.x)";
        config false;
      }
      leaf och-tx-act-power {
        yang:create-supported "false";
        yang:get-supported "true";
        yang:edit-supported "false";
        yang:delete-supported "false";
        type ciena-6500-types:STRING;
        description
          "TX actual power in dBm (xx.x)";
        config false;
      }
      leaf och-tx-min-power {
        yang:create-supported "false";
        yang:get-supported "true";
        yang:edit-supported "false";
        yang:delete-supported "false";
        type ciena-6500-types:STRING;
        description
          "TX minimum power in dBm (xx.x)";
        config false;
      }
      leaf och-tx-max-power {
        yang:create-supported "false";
        yang:get-supported "true";
        yang:edit-supported "false";
        yang:delete-supported "false";
        type ciena-6500-types:STRING;
        description
          "TX maximum power in dBm (xx.x)";
        config false;
      }
      leaf sd-th {
        default "6";
        yang:create-supported "true";
        yang:get-supported "false";
        yang:edit-supported "true";
        yang:delete-supported "false";
        type ciena-6500-types:INT {
          range "5..9";
        }
        description
          "Signal degrade threshold value";
        config true;
      }
    }
    list otm2 {
      yang:handler "tl1";
      yang:create-supported "true";
      yang:get-supported "true";
      yang:edit-supported "true";
      yang:delete-supported "true";
      key "otm2aid";
      config true;
      leaf otm2aid {
        mandatory true;
        description
          "AID in format OTM2-shelf-slot-port, OTM2-shelf-slot-portSsubport";
        type ciena-6500-types:aid;
      }
      leaf osid {
        yang:create-supported "true";
        yang:get-supported "true";
        yang:edit-supported "true";
        yang:delete-supported "false";
        type string {
          length "0..8";
        }
        description
          "8 Byte OSID identifier";
        config true;
      }
      leaf tx-sbs {
        yang:create-supported "true";
        yang:get-supported "true";
        yang:edit-supported "true";
        yang:delete-supported "false";
        type enumeration {
          enum ON {
            description
              "SBS Dither";
          }
          enum OFF;
        }
        default "ON";
        description
          "Stimulated Brillouin Scattering compensation Dither";
        config true;
      }
      leaf tx-am-frmt {
        yang:create-supported "true";
        yang:get-supported "true";
        yang:edit-supported "true";
        yang:delete-supported "false";
        type enumeration {
          enum OFF;
          enum AM2IDLER;
          enum AM1IDLER;
          enum AM2;
          enum AM1;
        }
        default "AM2";
        description
          "TX AM Format";
        config true;
      }
      leaf tx-fec-frmt {
        yang:create-supported "true";
        yang:get-supported "true";
        yang:edit-supported "true";
        yang:delete-supported "false";
        type enumeration {
          enum OFF {
            description
              "NO FEC";
          }
          enum PFEC {
            description
              "Product FEC";
          }
          enum RS8 {
            description
              "Reed Solomon 8";
          }
          enum UFEC {
            description
              "7% UFEC";
          }
          enum SCFEC {
            description
              "Super Concatenated FEC";
          }
          enum BCH20 {
            description
              "BCH20 FEC";
          }
          enum QFEC {
            description
              " QFEC";
          }
          enum EFEC {
            description
              "EFEC";
          }
          enum LDPCFEC {
            description
              "LDPCFEC";
          }
        }
        description
          "TX Supported FEC";
        config true;
      }
      leaf rx-fec-frmt {
        yang:create-supported "true";
        yang:get-supported "true";
        yang:edit-supported "true";
        yang:delete-supported "false";
        type enumeration {
          enum OFF {
            description
              "NO FEC";
          }
          enum PFEC {
            description
              "Product FEC";
          }
          enum RS8 {
            description
              "Reed Solomon 8";
          }
          enum UFEC {
            description
              "7% UFEC";
          }
          enum SCFEC {
            description
              "Super Concatenated FEC";
          }
          enum BCH20 {
            description
              "BCH20 FEC";
          }
        }
        description
          "RX Supported FEC";
        config true;
      }
      leaf otu-tx-tti {
        yang:create-supported "true";
        yang:get-supported "true";
        yang:edit-supported "true";
        yang:delete-supported "false";
        type ciena-6500-types:STRING;
        description
          "Transmitted TTI 32B. TTI = Trail Trace Identifier";
        config true;
      }
      leaf odu-tx-tti {
        yang:create-supported "true";
        yang:get-supported "true";
        yang:edit-supported "true";
        yang:delete-supported "false";
        type ciena-6500-types:STRING;
        description
          "Transmitted TTI 32B. TTI = Trail Trace Identifier";
        config true;
      }
      leaf otu-rx-exp-tti {
        yang:create-supported "true";
        yang:get-supported "true";
        yang:edit-supported "true";
        yang:delete-supported "false";
        type ciena-6500-types:STRING;
        description
          "Expected 32 Characters OTU TTI";
        config true;
      }
      leaf odu-rx-exp-tti {
        yang:create-supported "true";
        yang:get-supported "true";
        yang:edit-supported "true";
        yang:delete-supported "false";
        type ciena-6500-types:STRING;
        description
          "Expected 32 Characters ODU TTI";
        config true;
      }
      leaf otu-tx-sapi {
        yang:create-supported "true";
        yang:get-supported "true";
        yang:edit-supported "true";
        yang:delete-supported "false";
        type ciena-6500-types:STRING;
        description
          "OTU Transmitted SAPI TTI (15 Characters). TTI = Trail Trace Identifier";
        config true;
      }
      leaf otu-tx-dapi {
        yang:create-supported "true";
        yang:get-supported "true";
        yang:edit-supported "true";
        yang:delete-supported "false";
        type ciena-6500-types:STRING;
        description
          "OTU Transmitted DAPI TTI (15 Characters). TTI = Trail Trace Identifier";
        config true;
      }
      leaf otu-exp-sapi {
        yang:create-supported "true";
        yang:get-supported "true";
        yang:edit-supported "true";
        yang:delete-supported "false";
        type ciena-6500-types:STRING;
        description
          "OTU Expected SAPI TTI (15 Characters)";
        config true;
      }
      leaf otu-exp-dapi {
        yang:create-supported "true";
        yang:get-supported "true";
        yang:edit-supported "true";
        yang:delete-supported "false";
        type ciena-6500-types:STRING;
        description
          "OTU Expected DAPI TTI (15 Characters)";
        config true;
      }
      leaf odu-tx-sapi {
        yang:create-supported "true";
        yang:get-supported "true";
        yang:edit-supported "true";
        yang:delete-supported "false";
        type ciena-6500-types:STRING;
        description
          "ODU Transmitted SAPI TTI (15 Characters). TTI = Trail Trace Identifier";
        config true;
      }
      leaf odu-tx-dapi {
        yang:create-supported "true";
        yang:get-supported "true";
        yang:edit-supported "true";
        yang:delete-supported "false";
        type ciena-6500-types:STRING;
        description
          "ODU Transmitted DAPI TTI (15 Characters). TTI = Trail Trace Identifier";
        config true;
      }
      leaf odu-exp-sapi {
        yang:create-supported "true";
        yang:get-supported "true";
        yang:edit-supported "true";
        yang:delete-supported "false";
        type ciena-6500-types:STRING;
        description
          "ODU Expected SAPI TTI (15 Characters)";
        config true;
      }
      leaf odu-exp-dapi {
        yang:create-supported "true";
        yang:get-supported "true";
        yang:edit-supported "true";
        yang:delete-supported "false";
        type ciena-6500-types:STRING;
        description
          "ODU Expected DAPI TTI (15 Characters)";
        config true;
      }
      leaf tx-path-id {
        yang:create-supported "true";
        yang:get-supported "true";
        yang:edit-supported "true";
        yang:delete-supported "false";
        type ciena-6500-types:INT {
          range "1..254";
        }
        description
          "TX path identifier";
        config true;
      }
      leaf tx-tr-cont {
        yang:create-supported "true";
        yang:get-supported "true";
        yang:edit-supported "true";
        yang:delete-supported "false";
        type enumeration {
          enum OFF {
            description
              "Dispersion Control";
          }
          enum ON;
        }
        default "ON";
        description
          "TR Control";
        config true;
      }
      leaf tx-mode {
        yang:create-supported "true";
        yang:get-supported "true";
        yang:edit-supported "true";
        yang:delete-supported "false";
        type enumeration {
          enum ED {
            description
              "Extended Dispersion";
          }
          enum EP {
            description
              "Extended Power";
          }
        }
        default "ED";
        description
          "Transmitter Dispersion Mode";
        config true;
      }
      leaf tx-pwr {
        yang:create-supported "true";
        yang:get-supported "true";
        yang:edit-supported "true";
        yang:delete-supported "false";
        type ciena-6500-types:STRING;
        description
          "Provisioned TX Power in dBm (xx.x)";
        config true;
      }
      leaf tx-wvlngth-prov {
        default "0.00";
        yang:create-supported "true";
        yang:get-supported "true";
        yang:edit-supported "true";
        yang:delete-supported "false";
        type ciena-6500-types:STRING;
        description
          "Provisioned Wavelength in nm (xxxx.xx)";
        config true;
      }
      leaf tx-disp-prov {
        default "0";
        yang:create-supported "true";
        yang:get-supported "true";
        yang:edit-supported "true";
        yang:delete-supported "false";
        type ciena-6500-types:INT;
        description
          "Transmitter Dispersion Value";
        config true;
      }
      leaf port-mode {
        yang:create-supported "true";
        yang:get-supported "true";
        yang:edit-supported "false";
        yang:delete-supported "false";
        type enumeration {
          enum SONET {
            description
              "Optical port market";
          }
          enum SDH;
        }
        description
          "Optical port Market preference";
        config true;
      }
      leaf tf-mode {
        yang:create-supported "true";
        yang:get-supported "true";
        yang:edit-supported "true";
        yang:delete-supported "false";
        type enumeration {
          enum OFF {
            description
              "Alarms off, no traffic protection";
          }
          enum ALMONLY {
            description
              "Alarms on, no traffic protection";
          }
          enum LINEFAIL {
            description
              "Alarms on, with traffic protection";
          }
        }
        default "OFF";
        description
          "OTU Trace Fail Mode";
        config true;
      }
      leaf odu-tf-mode {
        yang:create-supported "true";
        yang:get-supported "true";
        yang:edit-supported "true";
        yang:delete-supported "false";
        type enumeration {
          enum OFF {
            description
              "Alarms off, no traffic protection";
          }
          enum ALMONLY {
            description
              "Alarms on, no traffic protection";
          }
        }
        default "OFF";
        description
          "ODU Trace Fail Mode";
        config true;
      }
      leaf otu-timen {
        yang:create-supported "true";
        yang:get-supported "true";
        yang:edit-supported "true";
        yang:delete-supported "false";
        type enumeration {
          enum OPERATOR {
            description
              "Monitor OTU Operator Specific TTI mismatch";
          }
          enum SAPI {
            description
              "Monitor OTU SAPI TTI mismatch";
          }
          enum DAPI {
            description
              "Monitor OTU DAPI TTI mismatch";
          }
          enum SAPI_DAPI {
            description
              "Monitor OTU SAPI and DAPI TTI mismatch";
          }
        }
        default "OPERATOR";
        description
          "OTU TTI Mismatch Detection";
        config true;
      }
      leaf odu-timen {
        yang:create-supported "true";
        yang:get-supported "true";
        yang:edit-supported "true";
        yang:delete-supported "false";
        type enumeration {
          enum OPERATOR {
            description
              "Monitor ODU Operator Specific TTI mismatch";
          }
          enum SAPI {
            description
              "Monitor ODU SAPI TTI mismatch";
          }
          enum DAPI {
            description
              "Monitor ODU DAPI TTI mismatch";
          }
          enum SAPI_DAPI {
            description
              "Monitor ODU SAPI and DAPI TTI mismatch";
          }
        }
        default "OPERATOR";
        description
          "ODU TTI Mismatch Detection";
        config true;
      }
      leaf laser-off-far-end-fail {
        yang:create-supported "true";
        yang:get-supported "true";
        yang:edit-supported "true";
        yang:delete-supported "false";
        type ciena-6500-enums:Laserofffarendfail;
        default "DISABLED";
        description
          "Enabled or Disabled LOL (Loss of Light) feature";
        config true;
      }
      leaf tx-chrip {
        yang:create-supported "true";
        yang:get-supported "true";
        yang:edit-supported "true";
        yang:delete-supported "false";
        type enumeration {
          enum POSITIVE;
          enum NEGATIVE;
        }
        default "NEGATIVE";
        description
          "Positive or Negative Chirp setting";
        config true;
      }
      leaf pre-fec-sf-th-lev {
        yang:create-supported "true";
        yang:get-supported "true";
        yang:edit-supported "true";
        yang:delete-supported "false";
        type ciena-6500-types:STRING;
        description
          "Pre-FEC Signal Fail Threshold Level. Parameter applies when FEC is ON";
        config true;
      }
      leaf pre-fec-sd-th-lev {
        yang:create-supported "true";
        yang:get-supported "true";
        yang:edit-supported "true";
        yang:delete-supported "false";
        type ciena-6500-types:STRING;
        description
          "Pre-FEC Signal Degrade Threshold Level. Parameter applies when FEC is ON";
        config true;
      }
      leaf otu-rate {
        yang:create-supported "true";
        yang:get-supported "true";
        yang:edit-supported "false";
        yang:delete-supported "false";
        type enumeration {
          enum 9G95 {
            description
              "9.95 G connection - Typically OC192 sonet";
          }
          enum 10G709 {
            description
              "10.70 G connection - Typically OTU2/OC192/STM64/10GE WAN";
          }
          enum 11G05 {
            description
              "11.05 G connection - Typically 10GE/OTU2 Mapping";
          }
          enum 11G09 {
            description
              "11.09 G connection - Typically 10GE/OTU2 Mapping";
          }
          enum 11G27 {
            description
              "11.27 G connection - Typically Fibre Channel 1200";
          }
        }
        default "10G709";
        description
          "Rate of OTU Connection";
        config true;
      }
      leaf odu-monitor {
        yang:create-supported "true";
        yang:get-supported "true";
        yang:edit-supported "true";
        yang:delete-supported "false";
        type enumeration {
          enum NO {
            description
              "Not monitor ODU Layer";
          }
          enum YES {
            description
              "Monitor ODU Layer";
          }
        }
        description
          "Indicating whether to monitor ODU Layer";
        config true;
      }
      leaf otu-sd-th-lev {
        yang:create-supported "true";
        yang:get-supported "true";
        yang:edit-supported "true";
        yang:delete-supported "false";
        type ciena-6500-types:INT;
        description
          "OTU Signal Degrade Threshold Level, only applies when FEC is OFF";
        config true;
      }
      leaf odu-sf-th-lev {
        default "0";
        yang:create-supported "true";
        yang:get-supported "true";
        yang:edit-supported "true";
        yang:delete-supported "false";
        type ciena-6500-types:INT;
        description
          "ODU Post-FEC Signal Fail Threshold Level";
        config true;
      }
      leaf odu-sd-th-lev {
        default "0";
        yang:create-supported "true";
        yang:get-supported "true";
        yang:edit-supported "true";
        yang:delete-supported "false";
        type ciena-6500-types:INT;
        description
          "ODU Post-FEC Signal Degrade Threshold Level";
        config true;
      }
      leaf cc-tx-freq {
        yang:create-supported "true";
        yang:get-supported "true";
        yang:edit-supported "true";
        yang:delete-supported "false";
        type ciena-6500-types:STRING;
        description
          "Tx Sub-carrier Frequency";
        config true;
      }
      leaf cc-tx-mod-depth {
        yang:create-supported "true";
        yang:get-supported "true";
        yang:edit-supported "true";
        yang:delete-supported "false";
        type ciena-6500-types:STRING;
        description
          "Tx Modulation Depth";
        config true;
      }
      leaf cc-tx-msg-len {
        default "16";
        yang:create-supported "true";
        yang:get-supported "true";
        yang:edit-supported "true";
        yang:delete-supported "false";
        type ciena-6500-types:STRING;
        description
          "Tx Message Length";
        config true;
      }
      leaf cc-tx-ask-baud-rate {
        yang:create-supported "true";
        yang:get-supported "true";
        yang:edit-supported "true";
        yang:delete-supported "false";
        type enumeration {
          enum 333.33 {
            description
              "Baud Rate(This value can be used in create and edit operations)";
          }
          enum 1667 {
            description
              "Baud Rate(This value can be used in create and edit operations)";
          }
          enum 150 {
            description
              "Baud Rate(This value can be used in create and edit operations)";
          }
          enum 1000 {
            description
              "Baud Rate(This value can be used in create and edit operations)";
          }
          enum UNKNOWN {
            description
              "Baud Rate";
          }
        }
        description
          "Tx ASK Baud Rate";
        config true;
      }
      leaf cc-tx-encode-frmt {
        yang:create-supported "true";
        yang:get-supported "true";
        yang:edit-supported "true";
        yang:delete-supported "false";
        type enumeration {
          enum NRZ {
            description
              "Encoding Format(This value can be used in create and edit operations)";
          }
          enum NRZ2 {
            description
              "Encoding Format(This value can be used in create and edit operations)";
          }
          enum 3SB1 {
            description
              "Encoding Format(This value can be used in create and edit operations)";
          }
          enum 3SB2 {
            description
              "Encoding Format(This value can be used in create and edit operations)";
          }
          enum UNKNOWN {
            description
              "UNKNOWN Encoding Format";
          }
        }
        description
          "Tx Encoding Format";
        config true;
      }
      leaf rc-rx-freq {
        yang:create-supported "true";
        yang:get-supported "true";
        yang:edit-supported "true";
        yang:delete-supported "false";
        type ciena-6500-types:STRING;
        description
          "Rx Sub-carrier Frequency";
        config true;
      }
      leaf rc-rx-msg-len {
        default "28";
        yang:create-supported "true";
        yang:get-supported "true";
        yang:edit-supported "true";
        yang:delete-supported "false";
        type ciena-6500-types:STRING;
        description
          "Rx Message Length of repeater system family A, C";
        config true;
      }
      leaf rc-rx-ask-baud-rate {
        yang:create-supported "true";
        yang:get-supported "true";
        yang:edit-supported "true";
        yang:delete-supported "false";
        type enumeration {
          enum 16.67 {
            description
              "Baud Rate(This value can be used in create and edit operations)";
          }
          enum 83.33 {
            description
              "Baud Rate(This value can be used in create and edit operations)";
          }
          enum 50 {
            description
              "Baud Rate(This value can be used in create and edit operations)";
          }
          enum UNKNOWN {
            description
              "UNKNOWN Baud Rate";
          }
        }
        default "16.67";
        description
          "Rx ASK Baud Rate";
        config true;
      }
      leaf rc-rx-decode-frmt {
        yang:create-supported "true";
        yang:get-supported "true";
        yang:edit-supported "true";
        yang:delete-supported "false";
        type enumeration {
          enum NRZ {
            description
              "Encoding Format(This value can be used in create and edit operations)";
          }
          enum NRZ2 {
            description
              "Encoding Format(This value can be used in create and edit operations)";
          }
          enum 3SB1 {
            description
              "Encoding Format(This value can be used in create and edit operations)";
          }
          enum 3SB2 {
            description
              "Encoding Format(This value can be used in create and edit operations)";
          }
          enum UNKNOWN {
            description
              "UNKNOWN Encoding Format";
          }
        }
        default "3SB1";
        description
          "Rx Decoding Format";
        config true;
      }
      leaf repeater-system-desc {
        yang:create-supported "true";
        yang:get-supported "true";
        yang:edit-supported "true";
        yang:delete-supported "false";
        type ciena-6500-types:STRING;
        description
          "Repeater Description";
        config true;
      }
      leaf rc-rx-thresh-mode {
        yang:create-supported "true";
        yang:get-supported "true";
        yang:edit-supported "true";
        yang:delete-supported "false";
        type enumeration {
          enum AUTO {
            description
              "Threshold Mode AUTO(This value can be used in create and edit operations)";
          }
          enum MANUAL {
            description
              "Threshold Mode MANUAL(This value can be used in create and edit operations)";
          }
          enum UNKNOWN {
            description
              "Threshold Mode UNKNOWN";
          }
        }
        default "AUTO";
        description
          "Rx Threshold Mode";
        config true;
      }
      leaf rc-rx-thresh {
        default "100";
        yang:create-supported "true";
        yang:get-supported "true";
        yang:edit-supported "true";
        yang:delete-supported "false";
        type ciena-6500-types:STRING;
        description
          "Rx Threshold";
        config true;
      }
      leaf clfi {
        yang:create-supported "true";
        yang:get-supported "true";
        yang:edit-supported "true";
        yang:delete-supported "false";
        type ciena-6500-types:STRING;
        description
          "Common Language Facility Identifier.Customer provisionable label for a facility.";
        config true;
      }
      leaf dm-enable {
        yang:create-supported "true";
        yang:get-supported "true";
        yang:edit-supported "true";
        yang:delete-supported "false";
        type enumeration {
          enum YES {
            description
              "Delay measurement is enabled.";
          }
          enum NO {
            description
              "Delay measurement is disabled.";
          }
        }
        default "NO";
        description
          "Enable or disable delay measurement.";
        config true;
      }
      leaf fec-sf-monitor {
        yang:create-supported "true";
        yang:get-supported "true";
        yang:edit-supported "true";
        yang:delete-supported "false";
        type enumeration {
          enum NO {
            description
              "Do Not monitor FECSF";
          }
          enum YES {
            description
              "Monitor FECSF";
          }
        }
        description
          "Indicates whether to monitor Far-End client signal";
        config true;
      }
      leaf otu-oh-non-term {
        yang:create-supported "true";
        yang:get-supported "true";
        yang:edit-supported "true";
        yang:delete-supported "false";
        type enumeration {
          enum NONE {
            description
              "Entire GCC OH terminated";
          }
          enum GCC0 {
            description
              "GCC0 portion of OTU OH not terminated";
          }
        }
        description
          "Indicating whether to termiate GCC OH or not";
        config true;
      }
      leaf encr-tcm {
        default "1";
        yang:create-supported "true";
        yang:get-supported "true";
        yang:edit-supported "true";
        yang:delete-supported "false";
        type ciena-6500-types:INT {
          range "1..6";
        }
        description
          "Active TCM Level for Encryption";
        config true;
      }
      leaf encr-odu1 {
        yang:create-supported "true";
        yang:get-supported "true";
        yang:edit-supported "true";
        yang:delete-supported "false";
        type ciena-6500-types:INT;
        description
          "ODU Reserve Byte 1 for Encryption";
        config true;
      }
      leaf encr-odu2 {
        yang:create-supported "true";
        yang:get-supported "true";
        yang:edit-supported "true";
        yang:delete-supported "false";
        type ciena-6500-types:INT;
        description
          "ODU Reserve Byte 2 for Encryption";
        config true;
      }
      leaf spli-mgmt {
        yang:create-supported "true";
        yang:get-supported "true";
        yang:edit-supported "true";
        yang:delete-supported "false";
        type ciena-6500-enums:spliMgmt;
        default "ON";
        description
          "Identify if Port is Manageable by SPLI";
        config true;
      }
      leaf pst {
        yang:create-supported "true";
        yang:get-supported "true";
        yang:edit-supported "false";
        yang:delete-supported "false";
        type enumeration {
          enum IS {
            description
              "In Service(This value can be used in create operation)";
          }
          enum IS-ANR {
            description
              "In Service - Abnormal";
          }
          enum OOS-MA {
            description
              "Out-of-service maintenance for provisioning manual administration(This value can be used in create operation)";
          }
          enum OOS-AU {
            description
              "Out-of-service autonomous from a failure detected point of view. It is not out of service from a state point of view. Alarm is raised if the entity is not able to perform its provisioned functions";
          }
          enum OOS-AUMA {
            description
              "Out-of-service autonomous management - the entity is not able to perform its provisioned functions and is purposefully removed from service";
          }
          enum OOS-MAANR {
            description
              "Out-of-service maintenance - abnormal.";
          }
        }
        default "IS";
        description
          "Identify the primary state";
        config true;
      }
      leaf-list sst {
        yang:create-supported "true";
        yang:get-supported "true";
        yang:edit-supported "true";
        yang:delete-supported "false";
        type enumeration {
          enum AINS {
            description
              "Auto-In-Service(This value can be used in create and edit operations)";
          }
          enum AINS-DEA {
            description
              "Auto-In-Service Deactivate(This value can be used in create and edit operations)";
          }
          enum MT {
            description
              "Maintenance(This value can be used in create operation)";
          }
          enum FLT {
            description
              "Fault detected";
          }
          enum SGEO {
            description
              "Supporting Entity Outage (based on PSTQ of OOS-AU, OOS-AUMA only)";
          }
          enum LPBK {
            description
              "Loopback";
          }
          enum DISCD {
            description
              "Disconnected. (no transparent traffic connection on this facility)";
          }
          enum TSGEN {
            description
              "Test set generation";
          }
          enum TSMON {
            description
              "Test set monitor";
          }
          enum WRKRX {
            description
              "Active OTM2 Facility in Receiving Direction (in protection configuration only)";
          }
          enum WRKTX {
            description
              "Active OTM2 Facility in Transmitting Direction (in protection configuration only)";
          }
          enum STBYH {
            description
              "Hot Standby (in protection configuration only)";
          }
          enum PSI {
            description
              "Protection Switch Inhibited (in protection configuration only)";
          }
        }
        description
          "Identify the secondary state";
        config true;
      }
      leaf exp-pt {
        yang:create-supported "false";
        yang:get-supported "true";
        yang:edit-supported "true";
        yang:delete-supported "false";
        type ciena-6500-types:STRING;
        description
          "HEX value in the range 0x00-0xFF. This attribute is used to specify the value of Expected PT.";
        config true;
      }
      leaf tx-pt {
        yang:create-supported "false";
        yang:get-supported "true";
        yang:edit-supported "true";
        yang:delete-supported "false";
        type ciena-6500-types:STRING;
        description
          "HEX value in the range 0x00-0xFF. This attribute is used to specify the value of Transmitted PT.";
        config true;
      }
      leaf rc-rx-bpsk-baud-rate {
        yang:create-supported "false";
        yang:get-supported "true";
        yang:edit-supported "true";
        yang:delete-supported "false";
        type enumeration {
          enum 150 {
            description
              "Baud Rate(This value can be used in edit operation)";
          }
          enum 5 {
            description
              "Baud Rate(This value can be used in edit operation)";
          }
          enum UNKNOWN {
            description
              "UNKNOWN Baud Rate";
          }
        }
        description
          "Rx BPSK Baud Rate";
        config true;
      }
      leaf repeater-system-type {
        yang:create-supported "false";
        yang:get-supported "true";
        yang:edit-supported "true";
        yang:delete-supported "false";
        type enumeration {
          enum FAMILY_A {
            description
              "Repeater System Family A";
          }
          enum FAMILY_B {
            description
              "Repeater System Family B";
          }
          enum FAMILY_C {
            description
              "Repeater System Family C";
          }
          enum UNKNOWN {
            description
              "Repeater System Type Unknown";
          }
        }
        description
          "Repeater System Type";
        config true;
      }
      leaf cond-type {
        yang:create-supported "false";
        yang:get-supported "true";
        yang:edit-supported "true";
        yang:delete-supported "false";
        type ciena-6500-enums:OTM_CONDTYPE;
        description
          "The type of conditioning";
        config true;
      }
      leaf odu-term {
        yang:create-supported "false";
        yang:get-supported "true";
        yang:edit-supported "false";
        yang:delete-supported "false";
        type enumeration {
          enum YES {
            description
              "Indicates that ODU TTI is terminated on this OTM2 facility.";
          }
          enum NO {
            description
              "Indicates that ODU TTI is not terminated on this OTM2 facility.";
          }
        }
        description
          "ODUTTITERM parameter has been introduced in the RTRV-OTM2 TL-1 commands. Values it takes on are ?YES? and ?NO?. ODUTTITERM values:?YES?: means that ODU TTI is terminated on this particular OTM2 facility and Site Manager should display ODU TTI and allow provisioning / monitoring of all ODU TTI parameters.?NO?: means that ODU TTI is not terminated on this port and SM should not display the ODU TTI parameters except the ODU TTI RX Incoming value. The 6500 BB packs (10GOTR/10GOTSC, 40GMUX, 2x10G OTR, 4x10G OTR, and OTNWT) that act as a regen will passthrough ODU TTI but will allow for the monitoring of ODU TTI RX Incoming value.When there is no client facilty, ODU TTI is not terminated. Default is NO since the client facility does not autoprov. If client facility is not an OTM2, then this port terminates ODU TTI (Terminal). If client facility is OTM2, then this port does not terminate ODU TTI (Regen).";
        config false;
      }
      leaf tx-act-pwr {
        yang:create-supported "false";
        yang:get-supported "true";
        yang:edit-supported "false";
        yang:delete-supported "false";
        type ciena-6500-types:STRING;
        description
          "TX actual power in dBm (xx.x)";
        config false;
      }
      leaf tx-min-pwr {
        yang:create-supported "false";
        yang:get-supported "true";
        yang:edit-supported "false";
        yang:delete-supported "false";
        type ciena-6500-types:STRING;
        description
          "TX minimum power in dBm (xx.x)";
        config false;
      }
      leaf tx-max-pwr {
        yang:create-supported "false";
        yang:get-supported "true";
        yang:edit-supported "false";
        yang:delete-supported "false";
        type ciena-6500-types:STRING;
        description
          "TX maximum power in dBm (xx.x)";
        config false;
      }
      leaf rx-act-pwr {
        yang:create-supported "false";
        yang:get-supported "true";
        yang:edit-supported "false";
        yang:delete-supported "false";
        type ciena-6500-types:STRING;
        description
          "RX actual power in dBm (xx.x)";
        config false;
      }
      leaf rx-min-pwr {
        yang:create-supported "false";
        yang:get-supported "true";
        yang:edit-supported "false";
        yang:delete-supported "false";
        type ciena-6500-types:STRING;
        description
          "RX minimum power in dBm (xx.x)";
        config false;
      }
      leaf rx-max-pwr {
        yang:create-supported "false";
        yang:get-supported "true";
        yang:edit-supported "false";
        yang:delete-supported "false";
        type ciena-6500-types:STRING;
        description
          "RX maximum power in dBm (xx.x)";
        config false;
      }
      leaf tx-wvlngth-min {
        default "0.00";
        yang:create-supported "false";
        yang:get-supported "true";
        yang:edit-supported "false";
        yang:delete-supported "false";
        type ciena-6500-types:STRING;
        description
          "Minimum Wavelength value in nm (xxxx.xx)";
        config false;
      }
      leaf tx-wvlngth-max {
        default "0.00";
        yang:create-supported "false";
        yang:get-supported "true";
        yang:edit-supported "false";
        yang:delete-supported "false";
        type ciena-6500-types:STRING;
        description
          "Maximum Wavelength value in nm (xxxx.xx)";
        config false;
      }
      leaf tx-wvlngth-spacing {
        yang:create-supported "false";
        yang:get-supported "true";
        yang:edit-supported "false";
        yang:delete-supported "false";
        type ciena-6500-types:STRING;
        description
          "OCH Wavelength Spacing";
        config false;
      }
      leaf tx-tr-cont-state {
        yang:create-supported "false";
        yang:get-supported "true";
        yang:edit-supported "false";
        yang:delete-supported "false";
        type enumeration {
          enum TRCONTOFF {
            description
              "TR Control OFF";
          }
          enum IDLE {
            description
              "TX Wavelength not provisioned.";
          }
          enum UNKNOWN;
          enum DISPSCANINPROG {
            description
              "Dispersion Scan in progress";
          }
          enum OOSOPTIMIZATION {
            description
              "Out of service optimization";
          }
          enum ISOPTIMIZATION {
            description
              "In service optimization";
          }
          enum ISOPTIMIZATIONHOLDOVER {
            description
              "In service optimization in Holdover";
          }
          enum SSOPTIMIZATION {
            description
              "Steady State Optimization";
          }
        }
        description
          "TR Control State";
        config false;
      }
      leaf tx-act-disp {
        yang:create-supported "false";
        yang:get-supported "true";
        yang:edit-supported "false";
        yang:delete-supported "false";
        type union {
          type enumeration {
            enum UNKNOWN;
          }
          type ciena-6500-types:INT;
        }
        description
          "Transmitter actual Dispersion Value";
        config false;
      }
      leaf tx-disp-min {
        yang:create-supported "false";
        yang:get-supported "true";
        yang:edit-supported "false";
        yang:delete-supported "false";
        type ciena-6500-types:INT;
        description
          "Minimum Transmitter Dispersion Value";
        config false;
      }
      leaf tx-disp-max {
        yang:create-supported "false";
        yang:get-supported "true";
        yang:edit-supported "false";
        yang:delete-supported "false";
        type ciena-6500-types:INT;
        description
          "Maximum Transmitter Dispersion Value";
        config false;
      }
      leaf rx-act-disp {
        yang:create-supported "false";
        yang:get-supported "true";
        yang:edit-supported "false";
        yang:delete-supported "false";
        type union {
          type enumeration {
            enum UNKNOWN;
          }
          type ciena-6500-types:INT;
        }
        description
          "TR Control RX Last Acquired Dispersion";
        config false;
      }
      leaf rx-echo-trace {
        yang:create-supported "false";
        yang:get-supported "true";
        yang:edit-supported "false";
        yang:delete-supported "false";
        type ciena-6500-types:STRING;
        description
          "TR Transmit Identifier Received";
        config false;
      }
      leaf tx-trace {
        yang:create-supported "false";
        yang:get-supported "true";
        yang:edit-supported "false";
        yang:delete-supported "false";
        type ciena-6500-types:STRING;
        description
          "TR Transmit Identifier Received Expected";
        config false;
      }
      leaf tx-assoc-far-end-rx {
        yang:create-supported "false";
        yang:get-supported "true";
        yang:edit-supported "false";
        yang:delete-supported "false";
        type ciena-6500-types:STRING;
        description
          "Transmitter associated far end receiver";
        config false;
      }
      leaf pre-fec-sf-th-ber {
        yang:create-supported "false";
        yang:get-supported "true";
        yang:edit-supported "false";
        yang:delete-supported "false";
        type ciena-6500-types:STRING;
        description
          "Pre-FEC Signal Fail Threshold Bit Error Rate. Parameter applies when FEC is ON";
        config false;
      }
      leaf pre-fec-sd-th-ber {
        yang:create-supported "false";
        yang:get-supported "true";
        yang:edit-supported "false";
        yang:delete-supported "false";
        type ciena-6500-types:STRING;
        description
          "Pre-FEC Signal Degrade Threshold Bit Error Rate. Parameter applies when FEC is ON";
        config false;
      }
      leaf opu2-resvd {
        yang:create-supported "false";
        yang:get-supported "true";
        yang:edit-supported "false";
        yang:delete-supported "false";
        type enumeration {
          enum YES {
            description
              "Use 7 unused bytes of the OPU2 overhead for payload";
          }
          enum NO;
        }
        description
          "This attribute is used to specify whether to use the 7 unused bytes of the OPU2 overhead for payload or not.";
        config false;
      }
      leaf ains-time-left {
        yang:create-supported "false";
        yang:get-supported "true";
        yang:edit-supported "false";
        yang:delete-supported "false";
        type ciena-6500-types:TIME;
        description
          "The format will be \"HH-MM\" for the time left in AINS timeout.";
        config false;
      }
      leaf otm-term {
        yang:create-supported "false";
        yang:get-supported "true";
        yang:edit-supported "false";
        yang:delete-supported "false";
        type ciena-6500-types:STRING;
        description
          "OTM Termination per layer (OPU and/or ODU and/or OTU)";
        config false;
      }
      leaf otm-flt-mon {
        yang:create-supported "false";
        yang:get-supported "true";
        yang:edit-supported "false";
        yang:delete-supported "false";
        type ciena-6500-types:STRING;
        description
          "OTM Fault Monitoring per layer (OPU and/or ODU and/or OTU)";
        config false;
      }
      leaf otm-prf-mon {
        yang:create-supported "false";
        yang:get-supported "true";
        yang:edit-supported "false";
        yang:delete-supported "false";
        type ciena-6500-types:STRING;
        description
          "OTM Performance Monitoring per layer (OPU and/or ODU and/or OTU)";
        config false;
      }
      leaf dm-count {
        yang:create-supported "false";
        yang:get-supported "true";
        yang:edit-supported "false";
        yang:delete-supported "false";
        type ciena-6500-types:STRING;
        description
          "Most recent delay measurement count.";
        config false;
      }
      leaf manual-trib-slots {
        yang:create-supported "false";
        yang:get-supported "true";
        yang:edit-supported "false";
        yang:delete-supported "false";
        type enumeration {
          enum NO {
            description
              "Manual tributary slots assignment is supported.";
          }
          enum YES {
            description
              "Manual tributary slots assignment is not supported.";
          }
        }
        description
          "Indicates whether tributary slot assignment is supported.";
        config false;
      }
      leaf ts-assigned {
        yang:create-supported "false";
        yang:get-supported "true";
        yang:edit-supported "false";
        yang:delete-supported "false";
        type ciena-6500-types:STRING;
        description
          "Assigned tributary slot(HEX) associated with this port.";
        config false;
      }
      leaf spli-managed {
        yang:create-supported "false";
        yang:get-supported "true";
        yang:edit-supported "false";
        yang:delete-supported "false";
        type ciena-6500-enums:spliManaged;
        description
          "Identify if Port is Currently Managed by SPLI";
        config false;
      }
      leaf differential-encoding {
        yang:create-supported "true";
        yang:get-supported "false";
        yang:edit-supported "true";
        yang:delete-supported "false";
        type enumeration {
          enum NONE {
            description
              "TR Control NONE";
          }
          enum HARD {
            description
              "TR Control HARD";
          }
          enum SOFT {
            description
              "TR Control SOFT";
          }
        }
        description
          "OCH Differential Encoding";
        config true;
      }
      leaf force {
        yang:create-supported "false";
        yang:get-supported "false";
        yang:edit-supported "true";
        yang:delete-supported "false";
        type enumeration {
          enum NO {
            description
              "Do Not Force Edit";
          }
          enum YES {
            description
              "Force Traffic Impacting Edit";
          }
        }
        default "NO";
        description
          "Indicating whether to force a traffic impacting edit to happen";
        config true;
      }
    }
    list otm3 {
      yang:handler "tl1";
      yang:create-supported "true";
      yang:get-supported "true";
      yang:edit-supported "true";
      yang:delete-supported "true";
      key "otm3aid";
      config true;
      leaf otm3aid {
        mandatory true;
        description
          "AID in format OTM3-shelf-slot-port";
        type ciena-6500-types:aid;
      }
      leaf osid {
        yang:create-supported "true";
        yang:get-supported "true";
        yang:edit-supported "true";
        yang:delete-supported "false";
        type string {
          length "0..8";
        }
        description
          "8 Byte OSID identifier";
        config true;
      }
      leaf tx-fec-frmt {
        yang:create-supported "true";
        yang:get-supported "true";
        yang:edit-supported "true";
        yang:delete-supported "false";
        type enumeration {
          enum OFF {
            description
              "NO FEC(This value can be used in create and edit operations)";
          }
          enum RS8 {
            description
              "Reed Solomon 8(This value can be used in create and edit operations)";
          }
          enum PFEC {
            description
              "Product FEC";
          }
        }
        description
          "TX Supported FEC";
        config true;
      }
      leaf rx-fec-frmt {
        yang:create-supported "true";
        yang:get-supported "true";
        yang:edit-supported "true";
        yang:delete-supported "false";
        type enumeration {
          enum OFF {
            description
              "NO FEC(This value can be used in create and edit operations)";
          }
          enum RS8 {
            description
              "Reed Solomon 8(This value can be used in create and edit operations)";
          }
          enum PFEC {
            description
              "Product FEC";
          }
        }
        description
          "RX Supported FEC";
        config true;
      }
      leaf otu-tx-tti {
        yang:create-supported "true";
        yang:get-supported "true";
        yang:edit-supported "true";
        yang:delete-supported "false";
        type ciena-6500-types:STRING;
        description
          "Transmitted OTU TTI 32B. TTI = Trail Trace Identifier";
        config true;
      }
      leaf odu-tx-tti {
        yang:create-supported "true";
        yang:get-supported "true";
        yang:edit-supported "true";
        yang:delete-supported "false";
        type ciena-6500-types:STRING;
        description
          "Transmitted ODU TTI 32B. TTI = Trail Trace Identifier";
        config true;
      }
      leaf otu-rx-exp-tti {
        yang:create-supported "true";
        yang:get-supported "true";
        yang:edit-supported "true";
        yang:delete-supported "false";
        type ciena-6500-types:STRING;
        description
          "Expected 32 Characters OTU TTI";
        config true;
      }
      leaf odu-rx-exp-tti {
        yang:create-supported "true";
        yang:get-supported "true";
        yang:edit-supported "true";
        yang:delete-supported "false";
        type ciena-6500-types:STRING;
        description
          "Expected 32 Characters ODU TTI";
        config true;
      }
      leaf otu-tx-sapi {
        yang:create-supported "true";
        yang:get-supported "true";
        yang:edit-supported "true";
        yang:delete-supported "false";
        type ciena-6500-types:STRING;
        description
          "OTU Transmitted SAPI TTI (15 Characters). TTI = Trail Trace Identifier";
        config true;
      }
      leaf otu-tx-dapi {
        yang:create-supported "true";
        yang:get-supported "true";
        yang:edit-supported "true";
        yang:delete-supported "false";
        type ciena-6500-types:STRING;
        description
          "OTU Transmitted DAPI TTI (15 Characters). TTI = Trail Trace Identifier";
        config true;
      }
      leaf otu-exp-sapi {
        yang:create-supported "true";
        yang:get-supported "true";
        yang:edit-supported "true";
        yang:delete-supported "false";
        type ciena-6500-types:STRING;
        description
          "OTU Expected SAPI TTI (15 Characters)";
        config true;
      }
      leaf otu-exp-dapi {
        yang:create-supported "true";
        yang:get-supported "true";
        yang:edit-supported "true";
        yang:delete-supported "false";
        type ciena-6500-types:STRING;
        description
          "OTU Expected DAPI TTI (15 Characters)";
        config true;
      }
      leaf odu-tx-sapi {
        yang:create-supported "true";
        yang:get-supported "true";
        yang:edit-supported "true";
        yang:delete-supported "false";
        type ciena-6500-types:STRING;
        description
          "ODU Transmitted SAPI TTI (15 Characters). TTI = Trail Trace Identifier";
        config true;
      }
      leaf odu-tx-dapi {
        yang:create-supported "true";
        yang:get-supported "true";
        yang:edit-supported "true";
        yang:delete-supported "false";
        type ciena-6500-types:STRING;
        description
          "ODU Transmitted DAPI TTI (15 Characters). TTI = Trail Trace Identifier";
        config true;
      }
      leaf odu-exp-sapi {
        yang:create-supported "true";
        yang:get-supported "true";
        yang:edit-supported "true";
        yang:delete-supported "false";
        type ciena-6500-types:STRING;
        description
          "ODU Expected SAPI TTI (15 Characters)";
        config true;
      }
      leaf odu-exp-dapi {
        yang:create-supported "true";
        yang:get-supported "true";
        yang:edit-supported "true";
        yang:delete-supported "false";
        type ciena-6500-types:STRING;
        description
          "ODU Expected DAPI TTI (15 Characters)";
        config true;
      }
      leaf tx-path-id {
        yang:create-supported "true";
        yang:get-supported "true";
        yang:edit-supported "true";
        yang:delete-supported "false";
        type ciena-6500-types:INT {
          range "1..254";
        }
        description
          "TX path identifier";
        config true;
      }
      leaf tx-pwr {
        yang:create-supported "true";
        yang:get-supported "true";
        yang:edit-supported "true";
        yang:delete-supported "false";
        type ciena-6500-types:STRING;
        description
          "Provisioned TX Power in dBm (xx.x)";
        config true;
      }
      leaf tx-wvlngth-prov {
        default "0.00";
        yang:create-supported "true";
        yang:get-supported "true";
        yang:edit-supported "true";
        yang:delete-supported "false";
        type ciena-6500-types:STRING;
        description
          "Provisioned Wavelength in nm (xxxx.xx)";
        config true;
      }
      leaf odu-monitor {
        yang:create-supported "true";
        yang:get-supported "true";
        yang:edit-supported "true";
        yang:delete-supported "false";
        type enumeration {
          enum NO {
            description
              "Not monitor ODU Layer";
          }
          enum YES {
            description
              "Monitor ODU Layer";
          }
        }
        description
          "Indicating whether to monitor ODU Layer";
        config true;
      }
      leaf port-mode {
        yang:create-supported "true";
        yang:get-supported "true";
        yang:edit-supported "false";
        yang:delete-supported "false";
        type enumeration {
          enum SONET;
          enum SDH;
        }
        description
          "Optical port Market preference. Default is from ED-SYS NEMODE";
        config true;
      }
      leaf tf-mode {
        yang:create-supported "true";
        yang:get-supported "true";
        yang:edit-supported "true";
        yang:delete-supported "false";
        type enumeration {
          enum OFF {
            description
              "Alarms off, no traffic protection";
          }
          enum ALMONLY {
            description
              "Alarms on, no traffic protection";
          }
          enum LINEFAIL {
            description
              "Alarms on, with traffic protection";
          }
        }
        default "OFF";
        description
          "OTU Trace Fail Mode";
        config true;
      }
      leaf odu-tf-mode {
        yang:create-supported "true";
        yang:get-supported "true";
        yang:edit-supported "true";
        yang:delete-supported "false";
        type enumeration {
          enum OFF {
            description
              "Alarms off, no traffic protection";
          }
          enum ALMONLY {
            description
              "Alarms on, no traffic protection";
          }
        }
        default "OFF";
        description
          "ODU Trace Fail Mode";
        config true;
      }
      leaf otu-timen {
        yang:create-supported "true";
        yang:get-supported "true";
        yang:edit-supported "true";
        yang:delete-supported "false";
        type enumeration {
          enum OPERATOR {
            description
              "Monitor OTU Operator Specific TTI mismatch";
          }
          enum SAPI {
            description
              "Monitor OTU SAPI TTI mismatch";
          }
          enum DAPI {
            description
              "Monitor OTU DAPI TTI mismatch";
          }
          enum SAPI_DAPI {
            description
              "Monitor OTU SAPI and DAPI TTI mismatch";
          }
        }
        default "OPERATOR";
        description
          "OTU TTI Mismatch Detection";
        config true;
      }
      leaf odu-timen {
        yang:create-supported "true";
        yang:get-supported "true";
        yang:edit-supported "true";
        yang:delete-supported "false";
        type enumeration {
          enum OPERATOR {
            description
              "Monitor ODU Operator Specific TTI mismatch";
          }
          enum SAPI {
            description
              "Monitor ODU SAPI TTI mismatch";
          }
          enum DAPI {
            description
              "Monitor ODU DAPI TTI mismatch";
          }
          enum SAPI_DAPI {
            description
              "Monitor ODU SAPI and DAPI TTI mismatch";
          }
        }
        default "OPERATOR";
        description
          "ODU TTI Mismatch Detection";
        config true;
      }
      leaf laser-off-far-end-fail {
        yang:create-supported "true";
        yang:get-supported "true";
        yang:edit-supported "true";
        yang:delete-supported "false";
        type ciena-6500-enums:Laserofffarendfail;
        default "DISABLED";
        description
          "Enabled or Disabled LOL (Loss of Light) feature";
        config true;
      }
      leaf pwr-bal-ctlr {
        yang:create-supported "true";
        yang:get-supported "true";
        yang:edit-supported "true";
        yang:delete-supported "false";
        type enumeration {
          enum DISABLED {
            description
              "Power Balance Controller Disabled";
          }
          enum ENABLED {
            description
              "Power Balance Controller Enabled";
          }
        }
        default "DISABLED";
        description
          "Provisioned Power Balance Controller Operating Mode";
        config true;
      }
      leaf pwr-bal-offset {
        yang:create-supported "true";
        yang:get-supported "true";
        yang:edit-supported "true";
        yang:delete-supported "false";
        type ciena-6500-types:STRING;
        description
          "Provisioned Power Balance Offset in dB (xx.x)";
        config true;
      }
      leaf tuning-mode {
        yang:create-supported "true";
        yang:get-supported "true";
        yang:edit-supported "true";
        yang:delete-supported "false";
        type enumeration {
          enum NORMAL {
            description
              "Normal Tuning Mode";
          }
          enum ACCELERATED {
            description
              "Accelerated Tuning Mode";
          }
        }
        default "NORMAL";
        description
          "Provisioned Tuning Mode";
        config true;
      }
      leaf pre-fec-sf-th-lev {
        yang:create-supported "true";
        yang:get-supported "true";
        yang:edit-supported "true";
        yang:delete-supported "false";
        type ciena-6500-types:STRING;
        description
          "Pre-FEC Signal Fail Threshold Level (decimal value in dBQ). Parameter applies when FEC is ON";
        config true;
      }
      leaf pre-fec-sd-th-lev {
        yang:create-supported "true";
        yang:get-supported "true";
        yang:edit-supported "true";
        yang:delete-supported "false";
        type ciena-6500-types:STRING;
        description
          "Pre-FEC Signal Degrade Threshold Level (decimal value in dBQ). Parameter applies when FEC is ON";
        config true;
      }
      leaf spectral-occupancy {
        yang:create-supported "true";
        yang:get-supported "true";
        yang:edit-supported "true";
        yang:delete-supported "false";
        type enumeration {
          enum NONE;
          enum NARROW;
          enum WIDE20;
          enum WIDE25;
          enum WIDE30;
          enum WIDE40;
          enum WIDE50;
          enum MINSPACE20;
          enum MINSPACE25;
        }
        description
          "OCH Spectral Occupancy setting";
        config true;
      }
      leaf odu-handoff {
        yang:create-supported "true";
        yang:get-supported "true";
        yang:edit-supported "true";
        yang:delete-supported "false";
        type enumeration {
          enum AUTO {
            description
              "Automatic Mapping";
          }
          enum ODU3 {
            description
              "ODU3 Mapping";
          }
          enum OC768 {
            description
              "OC768 Mapping";
          }
          enum ETH40G {
            description
              "ETH40G Mapping";
          }
          enum 4X10G1 {
            description
              "4X10G Mapping Mode 1";
          }
          enum 4X10G2 {
            description
              "4X10G Mapping Mode 2";
          }
          enum 4X10G3 {
            description
              "4X10G Mapping Mode 3";
          }
          enum 4X10G4 {
            description
              "4X10G Mapping Mode 4";
          }
          enum 4X10G5 {
            description
              "4X10G Mapping Mode 5";
          }
          enum 4X10G6 {
            description
              "4X10G Mapping Mode 6";
          }
        }
        default "AUTO";
        description
          "ODU Handoff Mapping Mode";
        config true;
      }
      leaf clfi {
        yang:create-supported "true";
        yang:get-supported "true";
        yang:edit-supported "true";
        yang:delete-supported "false";
        type ciena-6500-types:STRING;
        description
          "Common Language Facility Identifier.Customer provisionable label for a facility.";
        config true;
      }
      leaf frr {
        yang:create-supported "true";
        yang:get-supported "true";
        yang:edit-supported "true";
        yang:delete-supported "false";
        type enumeration {
          enum DISABLED {
            description
              "DISABLED Mode";
          }
          enum ENABLED {
            description
              "ENABLED Mode";
          }
        }
        default "DISABLED";
        description
          "OCH Fast Receiver Recovery";
        config true;
      }
      leaf frr-config {
        yang:create-supported "true";
        yang:get-supported "true";
        yang:edit-supported "true";
        yang:delete-supported "false";
        type enumeration {
          enum MATCHEDCD {
            description
              "Matched Chromatic Dispersion";
          }
          enum DIVERSECD2 {
            description
              "Diverse Chromatic Dispersion 2 Paths";
          }
        }
        default "MATCHEDCD";
        description
          "OCH FRR Network Configuration";
        config true;
      }
      leaf frr-path1-disp {
        default "AUTO";
        yang:create-supported "true";
        yang:get-supported "true";
        yang:edit-supported "true";
        yang:delete-supported "false";
        type ciena-6500-types:STRING;
        description
          "OCH FRR Link Dispersion for Path 1";
        config true;
      }
      leaf frr-path2-disp {
        default "AUTO";
        yang:create-supported "true";
        yang:get-supported "true";
        yang:edit-supported "true";
        yang:delete-supported "false";
        type ciena-6500-types:STRING;
        description
          "OCH FRR Link Dispersion for Path 2";
        config true;
      }
      leaf dm-enable {
        yang:create-supported "true";
        yang:get-supported "true";
        yang:edit-supported "true";
        yang:delete-supported "false";
        type enumeration {
          enum YES {
            description
              "Delay measurement is enabled.";
          }
          enum NO {
            description
              "Delay measurement is disabled.";
          }
        }
        default "NO";
        description
          "Enable or disable delay measurement.";
        config true;
      }
      leaf spli-mgmt {
        yang:create-supported "true";
        yang:get-supported "true";
        yang:edit-supported "true";
        yang:delete-supported "false";
        type ciena-6500-enums:spliMgmt;
        default "ON";
        description
          "Identify if Port is Manageable by SPLI";
        config true;
      }
      leaf pst {
        yang:create-supported "true";
        yang:get-supported "true";
        yang:edit-supported "false";
        yang:delete-supported "false";
        type enumeration {
          enum IS {
            description
              "In Service(This value can be used in create operation)";
          }
          enum IS-ANR {
            description
              "In Service - Abnormal";
          }
          enum OOS-MA {
            description
              "Out-of-service maintenance for provisioning manual administration(This value can be used in create operation)";
          }
          enum OOS-AU {
            description
              "Out-of-service autonomous from a failure detected point of view. It is not out of service from a state point of view. Alarm is raised if the entity is not able to perform its provisioned functions";
          }
          enum OOS-AUMA {
            description
              "Out-of-service autonomous management - the entity is not able to perform its provisioned functions and is purposefully removed from service";
          }
          enum OOS-MAANR {
            description
              "Out-of-service maintenance - abnormal.";
          }
        }
        default "IS";
        description
          "Identify the primary state";
        config true;
      }
      leaf-list sst {
        yang:create-supported "true";
        yang:get-supported "true";
        yang:edit-supported "true";
        yang:delete-supported "false";
        type enumeration {
          enum AINS {
            description
              "Auto-In-Service(This value can be used in create and edit operations)";
          }
          enum AINS-DEA {
            description
              "Auto-In-Service Deactivate(This value can be used in create and edit operations)";
          }
          enum MT {
            description
              "Maintenance(This value can be used in create operation)";
          }
          enum FLT {
            description
              "Fault detected";
          }
          enum SGEO {
            description
              "Supporting Entity Outage (based on PSTQ of OOS-AU, OOS-AUMA only)";
          }
          enum LPBK {
            description
              "Loopback";
          }
          enum DISCD {
            description
              "Disconnected. (no transparent traffic connection on this facility)";
          }
          enum TSGEN {
            description
              "Test set generation";
          }
          enum TSMON {
            description
              "Test set monitor";
          }
          enum WRKRX {
            description
              "Active OTM3 Facility in Receiving Direction (in protection configuration only)";
          }
          enum WRKTX {
            description
              "Active OTM3 Facility in Transmitting Direction (in protection configuration only)";
          }
          enum STBYH {
            description
              "Hot Standby (in protection configuration only)";
          }
          enum PSI {
            description
              "Protection Switch Inhibited (in protection configuration only)";
          }
        }
        description
          "Identify the secondary state";
        config true;
      }
      leaf cond-type {
        yang:create-supported "false";
        yang:get-supported "true";
        yang:edit-supported "true";
        yang:delete-supported "false";
        type ciena-6500-enums:OTM_CONDTYPE;
        description
          "The type of conditioning";
        config true;
      }
      leaf line-type {
        yang:create-supported "false";
        yang:get-supported "true";
        yang:edit-supported "true";
        yang:delete-supported "false";
        type ciena-6500-enums:linetype;
        description
          "OCH Line Sys Type";
        config true;
      }
      leaf odu-term {
        yang:create-supported "false";
        yang:get-supported "true";
        yang:edit-supported "false";
        yang:delete-supported "false";
        type enumeration {
          enum YES {
            description
              "Indicates that ODU TTI is terminated on this OTM3 facility.";
          }
          enum NO {
            description
              "Indicates that ODU TTI is not terminated on this OTM3 facility.";
          }
        }
        description
          "ODUTTITERM parameter values indicate:?YES?: means that ODU TTI is terminated on this particular OTM3 facility and Site Manager should display ODU TTI and allow provisioning / monitoring of all ODU TTI parameters.?NO?: means that ODU TTI is not terminated on this port and SM should not display the ODU TTI parameters except the ODU TTI RX Incoming value. The 6500 BB circuit packs that act as regen will passthrough ODU TTI but will allow for the monitoring of ODU TTI RX Incoming value.When there is no client facility, ODU TTI is not terminated. Default is NO since the client facility does not autoprov. If client facility is not an OTM3, then this port terminates ODU TTI (Terminal). If client facility is OTM3, then this port does not terminate ODU TTI (Regen).";
        config false;
      }
      leaf tx-act-high-pwr {
        yang:create-supported "false";
        yang:get-supported "true";
        yang:edit-supported "false";
        yang:delete-supported "false";
        type ciena-6500-types:STRING;
        description
          "TX Actual High Power Value in dBm (xx.x)";
        config false;
      }
      leaf tx-act-low-pwr {
        yang:create-supported "false";
        yang:get-supported "true";
        yang:edit-supported "false";
        yang:delete-supported "false";
        type ciena-6500-types:STRING;
        description
          "TX Actual Low Power Value in dBm (xx.x)";
        config false;
      }
      leaf tx-act-pwr {
        yang:create-supported "false";
        yang:get-supported "true";
        yang:edit-supported "false";
        yang:delete-supported "false";
        type ciena-6500-types:STRING;
        description
          "TX actual power in dBm (xx.x)";
        config false;
      }
      leaf tx-min-pwr {
        yang:create-supported "false";
        yang:get-supported "true";
        yang:edit-supported "false";
        yang:delete-supported "false";
        type ciena-6500-types:STRING;
        description
          "TX minimum power in dBm (xx.x)";
        config false;
      }
      leaf tx-max-pwr {
        yang:create-supported "false";
        yang:get-supported "true";
        yang:edit-supported "false";
        yang:delete-supported "false";
        type ciena-6500-types:STRING;
        description
          "TX maximum power in dBm (xx.x)";
        config false;
      }
      leaf rx-act-high-pwr {
        yang:create-supported "false";
        yang:get-supported "true";
        yang:edit-supported "false";
        yang:delete-supported "false";
        type ciena-6500-types:STRING;
        description
          "RX Actual High Power Value in dBm (xx.x)";
        config false;
      }
      leaf rx-act-low-pwr {
        yang:create-supported "false";
        yang:get-supported "true";
        yang:edit-supported "false";
        yang:delete-supported "false";
        type ciena-6500-types:STRING;
        description
          "RX Actual Low Power Value in dBm (xx.x)";
        config false;
      }
      leaf rx-act-pwr {
        yang:create-supported "false";
        yang:get-supported "true";
        yang:edit-supported "false";
        yang:delete-supported "false";
        type ciena-6500-types:STRING;
        description
          "RX actual power in dBm (xx.x)";
        config false;
      }
      leaf rx-min-pwr {
        yang:create-supported "false";
        yang:get-supported "true";
        yang:edit-supported "false";
        yang:delete-supported "false";
        type ciena-6500-types:STRING;
        description
          "RX minimum power in dBm (xx.x)";
        config false;
      }
      leaf rx-max-pwr {
        yang:create-supported "false";
        yang:get-supported "true";
        yang:edit-supported "false";
        yang:delete-supported "false";
        type ciena-6500-types:STRING;
        description
          "RX maximum power in dBm (xx.x)";
        config false;
      }
      leaf rx-ch-act-pwr {
        yang:create-supported "false";
        yang:get-supported "true";
        yang:edit-supported "false";
        yang:delete-supported "false";
        type ciena-6500-types:STRING;
        description
          "RX channel actual power in dBm (xx.x)";
        config false;
      }
      leaf rx-ch-min-pwr {
        yang:create-supported "false";
        yang:get-supported "true";
        yang:edit-supported "false";
        yang:delete-supported "false";
        type ciena-6500-types:STRING;
        description
          "RX channel minimum power in dBm (xx.x)";
        config false;
      }
      leaf rx-ch-max-pwr {
        yang:create-supported "false";
        yang:get-supported "true";
        yang:edit-supported "false";
        yang:delete-supported "false";
        type ciena-6500-types:STRING;
        description
          "RX channel maximum power in dBm (xx.x)";
        config false;
      }
      leaf pwr-bal-act-offset {
        yang:create-supported "false";
        yang:get-supported "true";
        yang:edit-supported "false";
        yang:delete-supported "false";
        type ciena-6500-types:STRING;
        description
          "Provisioned Power Balance Actual Offset in dB (xx.x)";
        config false;
      }
      leaf tx-wvlngth-min {
        default "0.00";
        yang:create-supported "false";
        yang:get-supported "true";
        yang:edit-supported "false";
        yang:delete-supported "false";
        type ciena-6500-types:STRING;
        description
          "Minimum Wavelength value in nm (xxxx.xx)";
        config false;
      }
      leaf tx-wvlngth-max {
        default "0.00";
        yang:create-supported "false";
        yang:get-supported "true";
        yang:edit-supported "false";
        yang:delete-supported "false";
        type ciena-6500-types:STRING;
        description
          "Maximum Wavelength value in nm (xxxx.xx)";
        config false;
      }
      leaf tx-wvlngth-spacing {
        yang:create-supported "false";
        yang:get-supported "true";
        yang:edit-supported "false";
        yang:delete-supported "false";
        type ciena-6500-types:STRING;
        description
          "OCH Wavelength Spacing";
        config false;
      }
      leaf differential-encoding {
        yang:create-supported "false";
        yang:get-supported "true";
        yang:edit-supported "false";
        yang:delete-supported "false";
        type enumeration {
          enum NONE {
            description
              "TR Control NONE";
          }
          enum HARD {
            description
              "TR Control HARD";
          }
          enum SOFT {
            description
              "TR Control SOFT";
          }
        }
        description
          "OCH Differential Encoding";
        config false;
      }
      leaf rx-act-disp {
        yang:create-supported "false";
        yang:get-supported "true";
        yang:edit-supported "false";
        yang:delete-supported "false";
        type union {
          type enumeration {
            enum UNKNOWN;
          }
          type ciena-6500-types:INT;
        }
        description
          "TR Control RX Last Acquired Dispersion";
        config false;
      }
      leaf max-pmd {
        yang:create-supported "false";
        yang:get-supported "true";
        yang:edit-supported "false";
        yang:delete-supported "false";
        type ciena-6500-types:STRING;
        description
          "Supported Mean DGD (Differential Group Delay) value";
        config false;
      }
      leaf rx-act-pmd {
        yang:create-supported "false";
        yang:get-supported "true";
        yang:edit-supported "false";
        yang:delete-supported "false";
        type ciena-6500-types:STRING;
        description
          "Estimated Instance of DGD (Differential Group Delay) value";
        config false;
      }
      leaf reach-spec {
        yang:create-supported "false";
        yang:get-supported "true";
        yang:edit-supported "false";
        yang:delete-supported "false";
        type ciena-6500-types:STRING;
        description
          "Reach Specification";
        config false;
      }
      leaf est-length {
        yang:create-supported "false";
        yang:get-supported "true";
        yang:edit-supported "false";
        yang:delete-supported "false";
        type ciena-6500-types:STRING;
        description
          "Estimated fiber length";
        config false;
      }
      leaf rtd {
        yang:create-supported "false";
        yang:get-supported "true";
        yang:edit-supported "false";
        yang:delete-supported "false";
        type ciena-6500-types:STRING;
        description
          "OCH Round Trip Delay.";
        config false;
      }
      leaf uni-latency {
        yang:create-supported "false";
        yang:get-supported "true";
        yang:edit-supported "false";
        yang:delete-supported "false";
        type ciena-6500-types:STRING;
        description
          "OCH Unidirectional Latency.";
        config false;
      }
      leaf rx-echo-trace {
        yang:create-supported "false";
        yang:get-supported "true";
        yang:edit-supported "false";
        yang:delete-supported "false";
        type ciena-6500-types:STRING;
        description
          "TR Transmit Identifier Received";
        config false;
      }
      leaf tx-trace {
        yang:create-supported "false";
        yang:get-supported "true";
        yang:edit-supported "false";
        yang:delete-supported "false";
        type ciena-6500-types:STRING;
        description
          "TR Transmit Identifier Received Expected";
        config false;
      }
      leaf tx-assoc-far-end-rx {
        yang:create-supported "false";
        yang:get-supported "true";
        yang:edit-supported "false";
        yang:delete-supported "false";
        type ciena-6500-types:STRING;
        description
          "Transmitter associated far end receiver";
        config false;
      }
      leaf otu-sd-th-lev {
        yang:create-supported "false";
        yang:get-supported "true";
        yang:edit-supported "false";
        yang:delete-supported "false";
        type ciena-6500-types:INT;
        description
          "OTU Signal Degrade Threshold Level, only applies when FEC is OFF";
        config false;
      }
      leaf odu-sf-th-lev {
        default "0";
        yang:create-supported "false";
        yang:get-supported "true";
        yang:edit-supported "false";
        yang:delete-supported "false";
        type ciena-6500-types:INT;
        description
          "ODU Post-FEC Signal Fail Threshold Level";
        config false;
      }
      leaf odu-sd-th-lev {
        default "0";
        yang:create-supported "false";
        yang:get-supported "true";
        yang:edit-supported "false";
        yang:delete-supported "false";
        type ciena-6500-types:INT;
        description
          "ODU Post-FEC Signal Degrade Threshold Level";
        config false;
      }
      leaf exp-pt {
        yang:create-supported "false";
        yang:get-supported "true";
        yang:edit-supported "false";
        yang:delete-supported "false";
        type ciena-6500-types:STRING;
        description
          "HEX value in the range 0x00-0xFF. This attribute is used to specify the value of Expected PT.";
        config false;
      }
      leaf tx-pt {
        yang:create-supported "false";
        yang:get-supported "true";
        yang:edit-supported "false";
        yang:delete-supported "false";
        type ciena-6500-types:STRING;
        description
          "HEX value in the range 0x00-0xFF. This attribute is used to specify the value of Transmitted PT.";
        config false;
      }
      leaf pre-fec-sf-th-ber {
        yang:create-supported "false";
        yang:get-supported "true";
        yang:edit-supported "false";
        yang:delete-supported "false";
        type ciena-6500-types:STRING;
        description
          "Pre-FEC Signal Fail Threshold Bit Error Rate. Parameter applies when FEC is ON";
        config false;
      }
      leaf pre-fec-sd-th-ber {
        yang:create-supported "false";
        yang:get-supported "true";
        yang:edit-supported "false";
        yang:delete-supported "false";
        type ciena-6500-types:STRING;
        description
          "Pre-FEC Signal Degrade Threshold Bit Error Rate. Parameter applies when FEC is ON";
        config false;
      }
      leaf otu-rate {
        yang:create-supported "false";
        yang:get-supported "true";
        yang:edit-supported "false";
        yang:delete-supported "false";
        type enumeration {
          enum 44G5 {
            description
              "44.5 G connection - Typically OTU3 Mapping";
          }
          enum 43G018 {
            description
              "43.018 G connection - Typically OTU3 40G rate";
          }
        }
        description
          "OTMn Rate";
        config false;
      }
      leaf ains-time-left {
        yang:create-supported "false";
        yang:get-supported "true";
        yang:edit-supported "false";
        yang:delete-supported "false";
        type ciena-6500-types:TIME;
        description
          "The format will be \"HH-MM\" for the time left in AINS timeout.";
        config false;
      }
      leaf otm-term {
        yang:create-supported "false";
        yang:get-supported "true";
        yang:edit-supported "false";
        yang:delete-supported "false";
        type ciena-6500-types:STRING;
        description
          "OTM Termination per layer (OPU and/or ODU and/or OTU)";
        config false;
      }
      leaf otm-flt-mon {
        yang:create-supported "false";
        yang:get-supported "true";
        yang:edit-supported "false";
        yang:delete-supported "false";
        type ciena-6500-types:STRING;
        description
          "OTM Fault Monitoring per layer (OPU and/or ODU and/or OTU)";
        config false;
      }
      leaf otm-prf-mon {
        yang:create-supported "false";
        yang:get-supported "true";
        yang:edit-supported "false";
        yang:delete-supported "false";
        type ciena-6500-types:STRING;
        description
          "OTM Performance Monitoring per layer (OPU and/or ODU and/or OTU)";
        config false;
      }
      leaf dm-count {
        yang:create-supported "false";
        yang:get-supported "true";
        yang:edit-supported "false";
        yang:delete-supported "false";
        type ciena-6500-types:STRING;
        description
          "Most recent delay measurement count.";
        config false;
      }
      leaf hold-off {
        default "0";
        yang:create-supported "false";
        yang:get-supported "true";
        yang:edit-supported "false";
        yang:delete-supported "false";
        type ciena-6500-types:INT;
        description
          "HoldOff signal conditioning timer";
        config false;
      }
      leaf hold-on {
        default "0";
        yang:create-supported "false";
        yang:get-supported "true";
        yang:edit-supported "false";
        yang:delete-supported "false";
        type ciena-6500-types:INT;
        description
          "HoldOn signal conditioning timer";
        config false;
      }
      leaf crs-rate {
        yang:create-supported "false";
        yang:get-supported "true";
        yang:edit-supported "false";
        yang:delete-supported "false";
        type enumeration {
          enum NIL {
            description
              "crsRate is not supported";
          }
          enum 4XODU2E {
            description
              "The connection rate is 4XODU2E";
          }
          enum ODU3 {
            description
              "The connection rate is ODU3";
          }
        }
        description
          "ODU connection rate";
        config false;
      }
      leaf spli-managed {
        yang:create-supported "false";
        yang:get-supported "true";
        yang:edit-supported "false";
        yang:delete-supported "false";
        type ciena-6500-enums:spliManaged;
        description
          "Identify if Port is Currently Managed by SPLI";
        config false;
      }
      leaf force {
        yang:create-supported "false";
        yang:get-supported "false";
        yang:edit-supported "true";
        yang:delete-supported "false";
        type enumeration {
          enum NO {
            description
              "Do Not Force Edit";
          }
          enum YES {
            description
              "Force Traffic Impacting Edit";
          }
        }
        default "NO";
        description
          "Indicating whether to force a traffic impacting edit to happen";
        config true;
      }
    }
    list otminfo {
      yang:handler "tl1";
      yang:create-supported "false";
      yang:get-supported "true";
      yang:edit-supported "false";
      yang:delete-supported "false";
      key "otmnaid";
      config false;
      leaf otmnaid {
        mandatory true;
        description
          "AID in format OTM2-shelf-slot-port, OTM2-shelf-slot-portSsubport, OTM3-shelf-slot-port, OTM4-shelf-slot-port, OTM0-shelf-slot-port, OTM1-shelf-slot-port, OTMFLEX-shelf-slot-port";
        type ciena-6500-types:aid;
      }
      leaf otu-rate-rx {
        yang:get-supported "true";
        type enumeration {
          enum 10G709 {
            description
              "10.70 G connection";
          }
          enum 11G05 {
            description
              "11.05 G connection";
          }
          enum 11G09 {
            description
              "11.09 G connection";
          }
          enum 112G {
            description
              "112 G connection";
          }
          enum UNAVAILABLE {
            description
              "Not Retreivable, Circuit pack missing or not ready";
          }
          enum UNKNOWN {
            description
              "Not Retreivable, Circuit pack cannot retrieve value";
          }
        }
        description
          "RX OTU Rate";
        config false;
      }
      leaf received-pt {
        yang:get-supported "true";
        type ciena-6500-types:STRING;
        description
          "Received Payload Type. HEX value in the range 0x00-0xFF";
        config false;
      }
    }
    list otm {
      yang:handler "tl1";
      yang:create-supported "true";
      yang:get-supported "true";
      yang:edit-supported "true";
      yang:delete-supported "true";
      key "otmaid";
      config true;
      leaf otmaid {
        mandatory true;
        description
          "AID in format OTM1-shelf-slot-port, OTM4-shelf-slot-port, OTMC2-shelf-slot-port, OTM-shelf-slot-port, OTM0-shelf-slot-port, OTMFLEX-shelf-slot-port";
        type ciena-6500-types:aid;
      }
      leaf osid {
        yang:create-supported "true";
        yang:get-supported "true";
        yang:edit-supported "true";
        yang:delete-supported "false";
        type string {
          length "0..8";
        }
        description
          "8 Byte OSID identifier";
        config true;
      }
      leaf tx-fec-frmt {
        yang:create-supported "true";
        yang:get-supported "true";
        yang:edit-supported "true";
        yang:delete-supported "false";
        type enumeration {
          enum OFF {
            description
              "NO FEC(This value can be used in create and edit operations)";
          }
          enum RS8 {
            description
              "Reed Solomon 8(This value can be used in create and edit operations)";
          }
          enum PFEC {
            description
              "Product FEC";
          }
          enum QFEC {
            description
              "QFEC";
          }
        }
        description
          "TX Supported FEC";
        config true;
      }
      leaf rx-fec-frmt {
        yang:create-supported "true";
        yang:get-supported "true";
        yang:edit-supported "true";
        yang:delete-supported "false";
        type enumeration {
          enum OFF {
            description
              "NO FEC(This value can be used in create and edit operations)";
          }
          enum RS8 {
            description
              "Reed Solomon 8(This value can be used in create and edit operations)";
          }
          enum PFEC {
            description
              "Product FEC";
          }
          enum QFEC {
            description
              "QFEC";
          }
        }
        description
          "RX Supported FEC";
        config true;
      }
      leaf otu-tx-tti {
        yang:create-supported "true";
        yang:get-supported "true";
        yang:edit-supported "true";
        yang:delete-supported "false";
        type ciena-6500-types:STRING;
        description
          "Transmitted OTU TTI 32B. TTI = Trail Trace Identifier";
        config true;
      }
      leaf otu-rx-exp-tti {
        yang:create-supported "true";
        yang:get-supported "true";
        yang:edit-supported "true";
        yang:delete-supported "false";
        type ciena-6500-types:STRING;
        description
          "Expected 32 Characters OTU TTI";
        config true;
      }
      leaf otu-tx-sapi {
        yang:create-supported "true";
        yang:get-supported "true";
        yang:edit-supported "true";
        yang:delete-supported "false";
        type ciena-6500-types:STRING;
        description
          "OTU Transmitted SAPI TTI (15 Characters). TTI = Trail Trace Identifier";
        config true;
      }
      leaf otu-tx-dapi {
        yang:create-supported "true";
        yang:get-supported "true";
        yang:edit-supported "true";
        yang:delete-supported "false";
        type ciena-6500-types:STRING;
        description
          "OTU Transmitted DAPI TTI (15 Characters). TTI = Trail Trace Identifier";
        config true;
      }
      leaf otu-exp-sapi {
        yang:create-supported "true";
        yang:get-supported "true";
        yang:edit-supported "true";
        yang:delete-supported "false";
        type ciena-6500-types:STRING;
        description
          "OTU Expected SAPI TTI (15 Characters)";
        config true;
      }
      leaf otu-exp-dapi {
        yang:create-supported "true";
        yang:get-supported "true";
        yang:edit-supported "true";
        yang:delete-supported "false";
        type ciena-6500-types:STRING;
        description
          "OTU Expected DAPI TTI (15 Characters)";
        config true;
      }
      leaf odu-tx-sapi {
        yang:create-supported "true";
        yang:get-supported "true";
        yang:edit-supported "true";
        yang:delete-supported "false";
        type ciena-6500-types:STRING;
        description
          "ODU Transmitted SAPI TTI (15 Characters). TTI = Trail Trace Identifier";
        config true;
      }
      leaf odu-tx-dapi {
        yang:create-supported "true";
        yang:get-supported "true";
        yang:edit-supported "true";
        yang:delete-supported "false";
        type ciena-6500-types:STRING;
        description
          "ODU Transmitted DAPI TTI (15 Characters). TTI = Trail Trace Identifier";
        config true;
      }
      leaf odu-exp-sapi {
        yang:create-supported "true";
        yang:get-supported "true";
        yang:edit-supported "true";
        yang:delete-supported "false";
        type ciena-6500-types:STRING;
        description
          "ODU Expected SAPI TTI (15 Characters)";
        config true;
      }
      leaf odu-exp-dapi {
        yang:create-supported "true";
        yang:get-supported "true";
        yang:edit-supported "true";
        yang:delete-supported "false";
        type ciena-6500-types:STRING;
        description
          "ODU Expected DAPI TTI (15 Characters)";
        config true;
      }
      leaf tx-path-id {
        yang:create-supported "true";
        yang:get-supported "true";
        yang:edit-supported "true";
        yang:delete-supported "false";
        type ciena-6500-types:INT {
          range "1..254";
        }
        description
          "TX path identifier";
        config true;
      }
      leaf tx-mode {
        yang:create-supported "true";
        yang:get-supported "true";
        yang:edit-supported "true";
        yang:delete-supported "false";
        type enumeration {
          enum MANUAL {
            description
              "Manual Precompensation Mode";
          }
          enum AUTOMATIC {
            description
              "Automatic Precompensation Mode";
          }
          enum CUSTOM1 {
            description
              "Custom1 Precompensation Mode";
          }
          enum OFF {
            description
              "No Precompensation Mode";
          }
          enum OFFSETAUTO {
            description
              "Offset Automatic Precompensation Mode";
          }
          enum EXTENDEDMANUAL {
            description
              "Extended Manual Precompensation Mode";
          }
        }
        description
          "Transmitter Dispersion Mode";
        config true;
      }
      leaf tx-disp-prov {
        yang:create-supported "true";
        yang:get-supported "true";
        yang:edit-supported "true";
        yang:delete-supported "false";
        type ciena-6500-types:INT;
        description
          "Transmitter Dispersion Value";
        config true;
      }
      leaf rotation {
        yang:create-supported "true";
        yang:get-supported "true";
        yang:edit-supported "true";
        yang:delete-supported "false";
        type enumeration {
          enum DISABLED {
            description
              "Disabled OCH Jones Rotation feature ";
          }
          enum ENABLED {
            description
              "Enabled OCH Jones Rotation feature";
          }
        }
        description
          "OCH Jones Rotation feature";
        config true;
      }
      leaf tx-pwr {
        yang:create-supported "true";
        yang:get-supported "true";
        yang:edit-supported "true";
        yang:delete-supported "false";
        type ciena-6500-types:STRING;
        description
          "Provisioned TX Power in dBm (xx.x)";
        config true;
      }
      leaf tx-wvlngth-prov {
        default "0.00";
        yang:create-supported "true";
        yang:get-supported "true";
        yang:edit-supported "true";
        yang:delete-supported "false";
        type ciena-6500-types:STRING;
        description
          "Provisioned Wavelength in nm (xxxx.xx)";
        config true;
      }
      leaf tx-wvlngth-spacing {
        yang:create-supported "true";
        yang:get-supported "true";
        yang:edit-supported "true";
        yang:delete-supported "false";
        type enumeration {
          enum 50 {
            description
              "50GHz";
          }
          enum FLEXGRID {
            description
              "FLEXGRID";
          }
        }
        default "50";
        description
          "OCH Wavelength Spacing";
        config true;
      }
      leaf differential-encoding {
        yang:create-supported "true";
        yang:get-supported "true";
        yang:edit-supported "true";
        yang:delete-supported "false";
        type enumeration {
          enum NONE {
            description
              "TR Control NONE";
          }
          enum HARD {
            description
              "TR Control HARD";
          }
          enum SOFT {
            description
              "TR Control SOFT";
          }
          enum XD {
            description
              "TR Control XD";
          }
        }
        description
          "OCH Differential Encoding";
        config true;
      }
      leaf odu-monitor {
        yang:create-supported "true";
        yang:get-supported "true";
        yang:edit-supported "true";
        yang:delete-supported "false";
        type enumeration {
          enum NO {
            description
              "Not monitor ODU Layer";
          }
          enum YES {
            description
              "Monitor ODU Layer";
          }
        }
        description
          "Indicating whether to monitor ODU Layer";
        config true;
      }
      leaf spectral-occupancy {
        yang:create-supported "true";
        yang:get-supported "true";
        yang:edit-supported "true";
        yang:delete-supported "false";
        type enumeration {
          enum NONE;
          enum NARROW;
          enum WIDE20;
          enum WIDE25;
          enum WIDE30;
          enum WIDE40;
          enum WIDE50;
          enum MINSPACE20;
          enum MINSPACE25;
        }
        description
          "OCH Spectral Occupancy setting";
        config true;
      }
      leaf odu-handoff {
        yang:create-supported "true";
        yang:get-supported "true";
        yang:edit-supported "true";
        yang:delete-supported "false";
        type enumeration {
          enum AUTO {
            description
              "Automatic Mapping";
          }
          enum ODU3 {
            description
              "ODU3 Mapping";
          }
          enum OC768 {
            description
              "OC768 Mapping";
          }
          enum ETH40G {
            description
              "ETH40G Mapping";
          }
          enum 4X10G1 {
            description
              "4X10G Mapping Mode 1";
          }
          enum 4X10G2 {
            description
              "4X10G Mapping Mode 2";
          }
          enum 4X10G3 {
            description
              "4X10G Mapping Mode 3";
          }
          enum 4X10G4 {
            description
              "4X10G Mapping Mode 4";
          }
          enum 4X10G5 {
            description
              "4X10G Mapping Mode 5";
          }
          enum 4X10G6 {
            description
              "4X10G Mapping Mode 6";
          }
          enum HALFODUALIGN {
            description
              "Master Slave - Half ODU Align Mapping Mode";
          }
        }
        default "AUTO";
        description
          "ODU Handoff Mapping Mode";
        config true;
      }
      leaf tuning-mode {
        yang:create-supported "true";
        yang:get-supported "true";
        yang:edit-supported "true";
        yang:delete-supported "false";
        type enumeration {
          enum NORMAL {
            description
              "Normal Tuning Mode";
          }
          enum ACCELERATED {
            description
              "Accelerated Tuning Mode";
          }
          enum FAST {
            description
              "Fast Tuning Mode";
          }
        }
        description
          "Provisioned Tuning Mode";
        config true;
      }
      leaf optimize-mode {
        yang:create-supported "true";
        yang:get-supported "true";
        yang:edit-supported "true";
        yang:delete-supported "false";
        type ciena-6500-enums:optimizeMode;
        description
          "Performance Optimization Mode";
        config true;
      }
      leaf port-mode {
        yang:create-supported "true";
        yang:get-supported "true";
        yang:edit-supported "false";
        yang:delete-supported "false";
        type enumeration {
          enum SONET;
          enum SDH;
        }
        description
          "Optical port Market preference. Default is from ED-SYS NEMODE";
        config true;
      }
      leaf tf-mode {
        yang:create-supported "true";
        yang:get-supported "true";
        yang:edit-supported "true";
        yang:delete-supported "false";
        type enumeration {
          enum OFF {
            description
              "Alarms off, no traffic protection";
          }
          enum ALMONLY {
            description
              "Alarms on, no traffic protection";
          }
          enum LINEFAIL {
            description
              "Alarms on, with traffic protection";
          }
        }
        default "OFF";
        description
          "OTU Trace Fail Mode";
        config true;
      }
      leaf odu-tf-mode {
        yang:create-supported "true";
        yang:get-supported "true";
        yang:edit-supported "true";
        yang:delete-supported "false";
        type enumeration {
          enum OFF {
            description
              "Alarms off, no traffic protection";
          }
          enum ALMONLY {
            description
              "Alarms on, no traffic protection";
          }
        }
        default "OFF";
        description
          "ODU Trace Fail Mode";
        config true;
      }
      leaf otu-timen {
        yang:create-supported "true";
        yang:get-supported "true";
        yang:edit-supported "true";
        yang:delete-supported "false";
        type enumeration {
          enum OPERATOR {
            description
              "Monitor OTU Operator Specific TTI mismatch";
          }
          enum SAPI {
            description
              "Monitor OTU SAPI TTI mismatch";
          }
          enum DAPI {
            description
              "Monitor OTU DAPI TTI mismatch";
          }
          enum SAPI_DAPI {
            description
              "Monitor OTU SAPI and DAPI TTI mismatch";
          }
        }
        default "OPERATOR";
        description
          "OTU TTI Mismatch Detection";
        config true;
      }
      leaf odu-timen {
        yang:create-supported "true";
        yang:get-supported "true";
        yang:edit-supported "true";
        yang:delete-supported "false";
        type enumeration {
          enum OPERATOR {
            description
              "Monitor ODU Operator Specific TTI mismatch";
          }
          enum SAPI {
            description
              "Monitor ODU SAPI TTI mismatch";
          }
          enum DAPI {
            description
              "Monitor ODU DAPI TTI mismatch";
          }
          enum SAPI_DAPI {
            description
              "Monitor ODU SAPI and DAPI TTI mismatch";
          }
        }
        default "OPERATOR";
        description
          "ODU TTI Mismatch Detection";
        config true;
      }
      leaf laser-off-far-end-fail {
        yang:create-supported "true";
        yang:get-supported "true";
        yang:edit-supported "true";
        yang:delete-supported "false";
        type ciena-6500-enums:Laserofffarendfail;
        default "DISABLED";
        description
          "Enabled or Disabled LOL (Loss of Light) feature";
        config true;
      }
      leaf frr {
        yang:create-supported "true";
        yang:get-supported "true";
        yang:edit-supported "true";
        yang:delete-supported "false";
        type enumeration {
          enum DISABLED {
            description
              "DISABLED Mode";
          }
          enum ENABLED {
            description
              "ENABLED Mode";
          }
        }
        default "DISABLED";
        description
          "OCH Fast Receiver Recovery";
        config true;
      }
      leaf frr-config {
        yang:create-supported "true";
        yang:get-supported "true";
        yang:edit-supported "true";
        yang:delete-supported "false";
        type enumeration {
          enum MATCHEDCD {
            description
              "Matched Chromatic Dispersion";
          }
          enum DIVERSECD2 {
            description
              "Diverse Chromatic Dispersion 2 Paths";
          }
        }
        default "MATCHEDCD";
        description
          "OCH FRR Network Configuration";
        config true;
      }
      leaf frr-path1-disp {
        default "AUTO";
        yang:create-supported "true";
        yang:get-supported "true";
        yang:edit-supported "true";
        yang:delete-supported "false";
        type ciena-6500-types:STRING;
        description
          "OCH FRR Link Dispersion for Path 1";
        config true;
      }
      leaf frr-path2-disp {
        default "AUTO";
        yang:create-supported "true";
        yang:get-supported "true";
        yang:edit-supported "true";
        yang:delete-supported "false";
        type ciena-6500-types:STRING;
        description
          "OCH FRR Link Dispersion for Path 2";
        config true;
      }
      leaf pre-fec-sf-th-lev {
        yang:create-supported "true";
        yang:get-supported "true";
        yang:edit-supported "true";
        yang:delete-supported "false";
        type ciena-6500-types:STRING;
        description
          "Pre-FEC Signal Fail Threshold Level (decimal value in dBQ). Parameter applies when FEC is ON";
        config true;
      }
      leaf pre-fec-sd-th-lev {
        yang:create-supported "true";
        yang:get-supported "true";
        yang:edit-supported "true";
        yang:delete-supported "false";
        type ciena-6500-types:STRING;
        description
          "Pre-FEC Signal Degrade Threshold Level (decimal value in dBQ). Parameter applies when FEC is ON";
        config true;
      }
      leaf otu-sd-th-lev {
        yang:create-supported "true";
        yang:get-supported "true";
        yang:edit-supported "true";
        yang:delete-supported "false";
        type ciena-6500-types:INT;
        description
          "OTU Signal Degrade Threshold Level, only applies when FEC is OFF";
        config true;
      }
      leaf odu-sf-th-lev {
        default "0";
        yang:create-supported "true";
        yang:get-supported "true";
        yang:edit-supported "true";
        yang:delete-supported "false";
        type ciena-6500-types:INT;
        description
          "ODU Post-FEC Signal Fail Threshold Level";
        config true;
      }
      leaf odu-sd-th-lev {
        default "0";
        yang:create-supported "true";
        yang:get-supported "true";
        yang:edit-supported "true";
        yang:delete-supported "false";
        type ciena-6500-types:INT;
        description
          "ODU Post-FEC Signal Degrade Threshold Level";
        config true;
      }
      leaf clfi {
        yang:create-supported "true";
        yang:get-supported "true";
        yang:edit-supported "true";
        yang:delete-supported "false";
        type ciena-6500-types:STRING;
        description
          "Common Language Facility Identifier.Customer provisionable label for a facility.";
        config true;
      }
      leaf otu-rate {
        yang:create-supported "true";
        yang:get-supported "true";
        yang:edit-supported "false";
        yang:delete-supported "false";
        type enumeration {
          enum 2G7 {
            description
              "2.7 G - OTM1(This value can be used in create operation)";
          }
          enum 112G {
            description
              "112 G connection - Typically OTU4 Mapping(This value can be used in create operation)";
          }
          enum OTUC2 {
            description
              "OTUC2 - 2x8QAM300G(This value can be used in create operation)";
          }
          enum 1G244 {
            description
              "1.244 G connection - OTM0";
          }
          enum 5G02 {
            description
              "5.02 G connection - OTMFLEX";
          }
          enum OTUC4-60 {
            description
              "OTUC4-60 Rate connection";
          }
          enum 2xOTU4 {
            description
              "2 x OTU4(112G) Rate connection";
          }
        }
        description
          "Rate of OTU Connection";
        config true;
      }
      leaf dm-enable {
        yang:create-supported "true";
        yang:get-supported "true";
        yang:edit-supported "true";
        yang:delete-supported "false";
        type enumeration {
          enum YES {
            description
              "Delay measurement is enabled.";
          }
          enum NO {
            description
              "Delay measurement is disabled.";
          }
        }
        default "NO";
        description
          "Enable or disable delay measurement.";
        config true;
      }
      leaf tx-freq-prov {
        yang:create-supported "true";
        yang:get-supported "true";
        yang:edit-supported "true";
        yang:delete-supported "false";
        type ciena-6500-types:STRING;
        description
          "Provisioned TX Frequency in THz (xxx.xxxx)";
        config true;
      }
      leaf enm-prov {
        yang:create-supported "true";
        yang:get-supported "true";
        yang:edit-supported "true";
        yang:delete-supported "false";
        type enumeration {
          enum MODE1 {
            description
              "ENM (Enhanced Non-linear Mitigation) mode 1(This value can be used in create and edit operations)";
          }
          enum MODE2 {
            description
              "ENM (Enhanced Non-linear Mitigation) mode 2(This value can be used in create and edit operations)";
          }
          enum AUTO {
            description
              "ENM (Enhanced Non-linear Mitigation) auto";
          }
        }
        description
          "Provisioned Enhanced Non-linear Mitigation mode";
        config true;
      }
      leaf carrier-centering-mode {
        yang:create-supported "true";
        yang:get-supported "true";
        yang:edit-supported "true";
        yang:delete-supported "false";
        type ciena-6500-enums:ochCarrierCenteringMode;
        description
          "Laser centering mode";
        config true;
      }
      leaf ccda {
        yang:create-supported "true";
        yang:get-supported "true";
        yang:edit-supported "true";
        yang:delete-supported "false";
        type ciena-6500-enums:ccda;
        description
          "TX Channel Contention Detection and Avoidance";
        config true;
      }
      leaf secure-oh {
        yang:create-supported "true";
        yang:get-supported "true";
        yang:edit-supported "true";
        yang:delete-supported "false";
        type ciena-6500-enums:SecureOH;
        description
          "Secure Overhead Bytes";
        config true;
      }
      leaf spli-mgmt {
        yang:create-supported "true";
        yang:get-supported "true";
        yang:edit-supported "true";
        yang:delete-supported "false";
        type ciena-6500-enums:spliMgmt;
        default "ON";
        description
          "Identify if Port is Manageable by SPLI";
        config true;
      }
      leaf encr-tcm {
        default "1";
        yang:create-supported "true";
        yang:get-supported "true";
        yang:edit-supported "true";
        yang:delete-supported "false";
        type ciena-6500-types:INT {
          range "1..6";
        }
        description
          "Active TCM Level for Encryption";
        config true;
      }
      leaf encr-odu1 {
        yang:create-supported "true";
        yang:get-supported "true";
        yang:edit-supported "true";
        yang:delete-supported "false";
        type ciena-6500-types:INT;
        description
          "ODU Reserve Byte 1 for Encryption";
        config true;
      }
      leaf encr-odu2 {
        yang:create-supported "true";
        yang:get-supported "true";
        yang:edit-supported "true";
        yang:delete-supported "false";
        type ciena-6500-types:INT;
        description
          "ODU Reserve Byte 2 for Encryption";
        config true;
      }
      leaf role {
        yang:create-supported "true";
        yang:get-supported "true";
        yang:edit-supported "false";
        yang:delete-supported "false";
        type enumeration {
          enum PRIME {
            description
              "Prime of the group.";
          }
          enum MEMBER2 {
            description
              "Member of the group.";
          }
        }
        description
          "Indicates whether this OTM facility is the prime or member in a 2X8QA3M00G group";
        config true;
      }
      leaf p-aid {
        yang:create-supported "true";
        yang:get-supported "true";
        yang:edit-supported "false";
        yang:delete-supported "false";
        type ciena-6500-types:IDENT;
        description
          "FLEX4 OCLD 2X8QAM300G CP group prime line port AID";
        config true;
      }
      leaf rx-pwr-l-thr {
        default "0";
        yang:create-supported "true";
        yang:get-supported "true";
        yang:edit-supported "true";
        yang:delete-supported "false";
        type ciena-6500-types:STRING;
        description
          "Provisioned Rx Power OOR low threshold";
        config true;
      }
      leaf rx-pwr-h-thr {
        default "0";
        yang:create-supported "true";
        yang:get-supported "true";
        yang:edit-supported "true";
        yang:delete-supported "false";
        type ciena-6500-types:STRING;
        description
          "Provisioned Rx Power OOR high threshold";
        config true;
      }
      leaf rx-ch-pwr-l-thr {
        default "0";
        yang:create-supported "true";
        yang:get-supported "true";
        yang:edit-supported "true";
        yang:delete-supported "false";
        type ciena-6500-types:STRING;
        description
          "Provisioned Rx channel Power OOR low threshold";
        config true;
      }
      leaf rx-ch-pwr-h-thr {
        default "0";
        yang:create-supported "true";
        yang:get-supported "true";
        yang:edit-supported "true";
        yang:delete-supported "false";
        type ciena-6500-types:STRING;
        description
          "Provisioned Rx channel Power OOR high threshold";
        config true;
      }
      leaf rx-pwr-thr-prov {
        yang:create-supported "true";
        yang:get-supported "true";
        yang:edit-supported "true";
        yang:delete-supported "false";
        type enumeration {
          enum ON {
            description
              "Use of provisioned thresholds is on";
          }
          enum OFF {
            description
              "Use of provisioned thresholds is off";
          }
        }
        default "OFF";
        description
          "Enable to use provisioned thresholds";
        config true;
      }
      leaf ttops {
        yang:create-supported "true";
        yang:get-supported "true";
        yang:edit-supported "true";
        yang:delete-supported "false";
        type ciena-6500-enums:BOOL_YES_NO;
        description
          "Transponder Triggered Switching Mode Enabled";
        config true;
      }
      leaf laser-centering-range {
        default "2.5 Ghz";
        yang:create-supported "true";
        yang:get-supported "true";
        yang:edit-supported "true";
        yang:delete-supported "false";
        type ciena-6500-types:STRING;
        description
          "Sets laser centering range";
        config true;
      }
      leaf laser-freq-thr {
        default "1.6";
        yang:create-supported "true";
        yang:get-supported "true";
        yang:edit-supported "true";
        yang:delete-supported "false";
        type decimal64 {
          range "0.0..3.0";
          fraction-digits 1;
        }
        description
          "Laser Frequency Threshold";
        config true;
      }
      leaf exp-res-time-prov {
        default "10";
        yang:create-supported "true";
        yang:get-supported "true";
        yang:edit-supported "true";
        yang:delete-supported "false";
        type ciena-6500-types:INT {
          range "0..255";
        }
        description
          "Provisioned Acquisition Holdoff Time";
        config true;
      }
      leaf optical-sf-rept {
        yang:create-supported "true";
        yang:get-supported "true";
        yang:edit-supported "true";
        yang:delete-supported "false";
        type enumeration {
          enum ON {
            description
              "Optical signal failed will be reported.";
          }
          enum OFF {
            description
              "Optical signal failed will not be reported.";
          }
        }
        default "OFF";
        description
          "Indicates whether or not the optical signal failed standing condition will be reported.";
        config true;
      }
      leaf pst {
        yang:create-supported "true";
        yang:get-supported "true";
        yang:edit-supported "false";
        yang:delete-supported "false";
        type enumeration {
          enum IS {
            description
              "In Service(This value can be used in create operation)";
          }
          enum IS-ANR {
            description
              "In Service - Abnormal";
          }
          enum OOS-MA {
            description
              "Out-of-service maintenance for provisioning manual administration(This value can be used in create operation)";
          }
          enum OOS-AU {
            description
              "Out-of-service autonomous from a failure detected point of view. It is not out of service from a state point of view. Alarm is raised if the entity is not able to perform its provisioned functions";
          }
          enum OOS-AUMA {
            description
              "Out-of-service autonomous management - the entity is not able to perform its provisioned functions and is purposefully removed from service";
          }
          enum OOS-MAANR {
            description
              "Out-of-service maintenance - abnormal.";
          }
        }
        default "IS";
        description
          "Identify the primary state";
        config true;
      }
      leaf-list sst {
        yang:create-supported "true";
        yang:get-supported "true";
        yang:edit-supported "true";
        yang:delete-supported "false";
        type enumeration {
          enum AINS {
            description
              "Auto-In-Service(This value can be used in create and edit operations)";
          }
          enum AINS-DEA {
            description
              "Auto-In-Service Deactivate(This value can be used in create and edit operations)";
          }
          enum MT {
            description
              "Maintenance(This value can be used in create operation)";
          }
          enum FLT {
            description
              "Fault detected";
          }
          enum SGEO {
            description
              "Supporting Entity Outage (based on PSTQ of OOS-AU, OOS-AUMA only)";
          }
          enum LPBK {
            description
              "Loopback";
          }
          enum DISCD {
            description
              "Disconnected. (no transparent traffic connection on this facility)";
          }
          enum TSGEN {
            description
              "Test set generation";
          }
          enum TSMON {
            description
              "Test set monitor";
          }
          enum WRKRX {
            description
              "Active OTM Facility in Receiving Direction (in protection configuration only)";
          }
          enum WRKTX {
            description
              "Active OTM Facility in Transmitting Direction (in protection configuration only)";
          }
          enum STBYH {
            description
              "Hot Standby (in protection configuration only)";
          }
          enum PSI {
            description
              "Protection Switch Inhibited (in protection configuration only)";
          }
        }
        description
          "Identify the secondary state.";
        config true;
      }
      leaf odu-tx-tti {
        yang:create-supported "false";
        yang:get-supported "true";
        yang:edit-supported "true";
        yang:delete-supported "false";
        type ciena-6500-types:STRING;
        description
          "Transmitted ODU TTI (Trail Trace Identifier), 32B. Last 32 bytes of the allocated 64 byte TTI allocation are used.";
        config true;
      }
      leaf odu-rx-exp-tti {
        yang:create-supported "false";
        yang:get-supported "true";
        yang:edit-supported "true";
        yang:delete-supported "false";
        type ciena-6500-types:STRING;
        description
          "Expected 32 Characters ODU TTI";
        config true;
      }
      leaf exp-pt {
        yang:create-supported "false";
        yang:get-supported "true";
        yang:edit-supported "true";
        yang:delete-supported "false";
        type ciena-6500-types:STRING;
        description
          "HEX value in the range 0x00-0xFF. This attribute is used to specify the value of Expected PT.";
        config true;
      }
      leaf tx-pt {
        yang:create-supported "false";
        yang:get-supported "true";
        yang:edit-supported "true";
        yang:delete-supported "false";
        type ciena-6500-types:STRING;
        description
          "HEX value in the range 0x00-0xFF. This attribute is used to specify the value of Transmitted PT.";
        config true;
      }
      leaf txb {
        yang:create-supported "false";
        yang:get-supported "true";
        yang:edit-supported "true";
        yang:delete-supported "false";
        type ciena-6500-enums:txb;
        description
          "TX Power in Reduced State";
        config true;
      }
      leaf line-type {
        yang:create-supported "false";
        yang:get-supported "true";
        yang:edit-supported "true";
        yang:delete-supported "false";
        type ciena-6500-enums:linetype;
        description
          "OCH Line Sys Type";
        config true;
      }
      leaf odu-term {
        yang:create-supported "false";
        yang:get-supported "true";
        yang:edit-supported "false";
        yang:delete-supported "false";
        type enumeration {
          enum YES {
            description
              "Indicates that ODU TTI is terminated on this OTM facility.";
          }
          enum NO {
            description
              "Indicates that ODU TTI is not terminated on this OTM facility.";
          }
        }
        description
          "ODUTTITERM parameter values indicate:?YES?: means that ODU TTI is terminated on this particular OTM facility and Site Manager should display ODU TTI and allow provisioning / monitoring of all ODU TTI parameters.?NO?: means that ODU TTI is not terminated on this port and SM should not display the ODU TTI parameters except the ODU TTI RX Incoming value. The 6500 BB circuit packs that act as regen will passthrough ODU TTI but will allow for the monitoring of ODU TTI RX Incoming value.When there is no client facility, ODU TTI is not terminated. Default is NO since the client facility does not autoprov. If client facility is not an OTM, then this port terminates ODU TTI (Terminal). If client facility is OTM, then this port does not terminate ODU TTI (Regen).";
        config false;
      }
      leaf tx-act-disp {
        yang:create-supported "false";
        yang:get-supported "true";
        yang:edit-supported "false";
        yang:delete-supported "false";
        type union {
          type enumeration {
            enum UNKNOWN;
          }
          type ciena-6500-types:INT;
        }
        description
          "Transmitter total actual link dispersion in the near-to-far direction";
        config false;
      }
      leaf tx-disp-min {
        yang:create-supported "false";
        yang:get-supported "true";
        yang:edit-supported "false";
        yang:delete-supported "false";
        type ciena-6500-types:INT;
        description
          "Minimum Transmitter Dispersion Value";
        config false;
      }
      leaf tx-disp-max {
        yang:create-supported "false";
        yang:get-supported "true";
        yang:edit-supported "false";
        yang:delete-supported "false";
        type ciena-6500-types:INT;
        description
          "Maximum Transmitter Dispersion Value";
        config false;
      }
      leaf rx-act-disp {
        yang:create-supported "false";
        yang:get-supported "true";
        yang:edit-supported "false";
        yang:delete-supported "false";
        type union {
          type enumeration {
            enum UNKNOWN;
          }
          type ciena-6500-types:INT;
        }
        description
          "Receiver total actual link dispersion in the far-to-near direction";
        config false;
      }
      leaf tx-pre-disp {
        yang:create-supported "false";
        yang:get-supported "true";
        yang:edit-supported "false";
        yang:delete-supported "false";
        type union {
          type enumeration {
            enum UNKNOWN;
          }
          type ciena-6500-types:INT;
        }
        description
          "Tx Precompensation Dispersion Value.";
        config false;
      }
      leaf rx-post-disp {
        yang:create-supported "false";
        yang:get-supported "true";
        yang:edit-supported "false";
        yang:delete-supported "false";
        type union {
          type enumeration {
            enum UNKNOWN;
          }
          type ciena-6500-types:INT;
        }
        description
          "Rx Postcompensation Dispersion Value.";
        config false;
      }
      leaf tx-act-pwr {
        yang:create-supported "false";
        yang:get-supported "true";
        yang:edit-supported "false";
        yang:delete-supported "false";
        type ciena-6500-types:STRING;
        description
          "TX actual power in dBm (xx.x)";
        config false;
      }
      leaf tx-min-pwr {
        yang:create-supported "false";
        yang:get-supported "true";
        yang:edit-supported "false";
        yang:delete-supported "false";
        type ciena-6500-types:STRING;
        description
          "TX minimum power in dBm (xx.x)";
        config false;
      }
      leaf tx-max-pwr {
        yang:create-supported "false";
        yang:get-supported "true";
        yang:edit-supported "false";
        yang:delete-supported "false";
        type ciena-6500-types:STRING;
        description
          "TX maximum power in dBm (xx.x)";
        config false;
      }
      leaf rx-act-pwr {
        yang:create-supported "false";
        yang:get-supported "true";
        yang:edit-supported "false";
        yang:delete-supported "false";
        type ciena-6500-types:STRING;
        description
          "RX actual power in dBm (xx.x)";
        config false;
      }
      leaf rx-min-pwr {
        yang:create-supported "false";
        yang:get-supported "true";
        yang:edit-supported "false";
        yang:delete-supported "false";
        type ciena-6500-types:STRING;
        description
          "RX minimum power in dBm (xx.x)";
        config false;
      }
      leaf rx-max-pwr {
        yang:create-supported "false";
        yang:get-supported "true";
        yang:edit-supported "false";
        yang:delete-supported "false";
        type ciena-6500-types:STRING;
        description
          "RX maximum power in dBm (xx.x)";
        config false;
      }
      leaf rx-ch-act-pwr {
        yang:create-supported "false";
        yang:get-supported "true";
        yang:edit-supported "false";
        yang:delete-supported "false";
        type ciena-6500-types:STRING;
        description
          "RX channel actual power in dBm (xx.x)";
        config false;
      }
      leaf rx-ch-min-pwr {
        yang:create-supported "false";
        yang:get-supported "true";
        yang:edit-supported "false";
        yang:delete-supported "false";
        type ciena-6500-types:STRING;
        description
          "RX channel minimum power in dBm (xx.x)";
        config false;
      }
      leaf rx-ch-max-pwr {
        yang:create-supported "false";
        yang:get-supported "true";
        yang:edit-supported "false";
        yang:delete-supported "false";
        type ciena-6500-types:STRING;
        description
          "RX channel maximum power in dBm (xx.x)";
        config false;
      }
      leaf pwr-bal-ctlr {
        yang:create-supported "false";
        yang:get-supported "true";
        yang:edit-supported "false";
        yang:delete-supported "false";
        type enumeration {
          enum DISABLED {
            description
              "Power Balance Controller Disabled";
          }
          enum ENABLED {
            description
              "Power Balance Controller Enabled";
          }
        }
        description
          "Provisioned Power Balance Controller Operating Mode";
        config false;
      }
      leaf pwr-bal-offset {
        yang:create-supported "false";
        yang:get-supported "true";
        yang:edit-supported "false";
        yang:delete-supported "false";
        type ciena-6500-types:STRING;
        description
          "Provisioned Power Balance Offset in dB (xx.x)";
        config false;
      }
      leaf pwr-bal-act-offset {
        yang:create-supported "false";
        yang:get-supported "true";
        yang:edit-supported "false";
        yang:delete-supported "false";
        type ciena-6500-types:STRING;
        description
          "Provisioned Power Balance Actual Offset in dB (xx.x)";
        config false;
      }
      leaf tx-act-high-pwr {
        yang:create-supported "false";
        yang:get-supported "true";
        yang:edit-supported "false";
        yang:delete-supported "false";
        type ciena-6500-types:STRING;
        description
          "TX Actual High Power Value in dBm (xx.x)";
        config false;
      }
      leaf tx-act-low-pwr {
        yang:create-supported "false";
        yang:get-supported "true";
        yang:edit-supported "false";
        yang:delete-supported "false";
        type ciena-6500-types:STRING;
        description
          "TX Actual Low Power Value in dBm (xx.x)";
        config false;
      }
      leaf rx-act-high-pwr {
        yang:create-supported "false";
        yang:get-supported "true";
        yang:edit-supported "false";
        yang:delete-supported "false";
        type ciena-6500-types:STRING;
        description
          "RX Actual High Power Value in dBm (xx.x)";
        config false;
      }
      leaf rx-act-low-pwr {
        yang:create-supported "false";
        yang:get-supported "true";
        yang:edit-supported "false";
        yang:delete-supported "false";
        type ciena-6500-types:STRING;
        description
          "RX Actual Low Power Value in dBm (xx.x)";
        config false;
      }
      leaf-list tx-act-ln-pwr {
        yang:create-supported "false";
        yang:get-supported "true";
        yang:edit-supported "false";
        yang:delete-supported "false";
        type ciena-6500-types:STRING;
        description
          "Lane TX Power Value in dBm (xx.x)";
        config false;
      }
      leaf-list rx-act-ln-pwr {
        yang:create-supported "false";
        yang:get-supported "true";
        yang:edit-supported "false";
        yang:delete-supported "false";
        type ciena-6500-types:STRING;
        description
          "Lane RX Power Value in dBm (xx.x)";
        config false;
      }
      leaf tx-wvlngth-min {
        default "0.00";
        yang:create-supported "false";
        yang:get-supported "true";
        yang:edit-supported "false";
        yang:delete-supported "false";
        type ciena-6500-types:STRING;
        description
          "Minimum Wavelength value in nm (xxxx.xx)";
        config false;
      }
      leaf tx-wvlngth-max {
        default "0.00";
        yang:create-supported "false";
        yang:get-supported "true";
        yang:edit-supported "false";
        yang:delete-supported "false";
        type ciena-6500-types:STRING;
        description
          "Maximum Wavelength value in nm (xxxx.xx)";
        config false;
      }
      leaf max-pmd {
        yang:create-supported "false";
        yang:get-supported "true";
        yang:edit-supported "false";
        yang:delete-supported "false";
        type ciena-6500-types:STRING;
        description
          "Supported Mean DGD (Differential Group Delay) value";
        config false;
      }
      leaf rx-act-pmd {
        yang:create-supported "false";
        yang:get-supported "true";
        yang:edit-supported "false";
        yang:delete-supported "false";
        type ciena-6500-types:STRING;
        description
          "Estimated Instance of DGD (Differential Group Delay) value";
        config false;
      }
      leaf reach-spec {
        yang:create-supported "false";
        yang:get-supported "true";
        yang:edit-supported "false";
        yang:delete-supported "false";
        type ciena-6500-types:STRING;
        description
          "Reach Specification";
        config false;
      }
      leaf est-length {
        yang:create-supported "false";
        yang:get-supported "true";
        yang:edit-supported "false";
        yang:delete-supported "false";
        type ciena-6500-types:STRING;
        description
          "Estimated fiber length";
        config false;
      }
      leaf rtd {
        yang:create-supported "false";
        yang:get-supported "true";
        yang:edit-supported "false";
        yang:delete-supported "false";
        type ciena-6500-types:STRING;
        description
          "OCH Round Trip Delay.";
        config false;
      }
      leaf uni-latency {
        yang:create-supported "false";
        yang:get-supported "true";
        yang:edit-supported "false";
        yang:delete-supported "false";
        type ciena-6500-types:STRING;
        description
          "OCH Unidirectional Latency.";
        config false;
      }
      leaf rx-echo-trace {
        yang:create-supported "false";
        yang:get-supported "true";
        yang:edit-supported "false";
        yang:delete-supported "false";
        type ciena-6500-types:STRING;
        description
          "TR Transmit Identifier Received";
        config false;
      }
      leaf tx-trace {
        yang:create-supported "false";
        yang:get-supported "true";
        yang:edit-supported "false";
        yang:delete-supported "false";
        type ciena-6500-types:STRING;
        description
          "TR Transmit Identifier Received Expected";
        config false;
      }
      leaf tx-assoc-far-end-rx {
        yang:create-supported "false";
        yang:get-supported "true";
        yang:edit-supported "false";
        yang:delete-supported "false";
        type ciena-6500-types:STRING;
        description
          "Transmitter associated far end receiver";
        config false;
      }
      leaf tx-chrip {
        yang:create-supported "false";
        yang:get-supported "true";
        yang:edit-supported "false";
        yang:delete-supported "false";
        type enumeration {
          enum POSITIVE;
          enum NEGATIVE;
        }
        description
          "Positive or Negative Chirp setting";
        config false;
      }
      leaf pre-fec-sf-th-ber {
        yang:create-supported "false";
        yang:get-supported "true";
        yang:edit-supported "false";
        yang:delete-supported "false";
        type ciena-6500-types:STRING;
        description
          "Pre-FEC Signal Fail Threshold Bit Error Rate. Parameter applies when FEC is ON";
        config false;
      }
      leaf pre-fec-sd-th-ber {
        yang:create-supported "false";
        yang:get-supported "true";
        yang:edit-supported "false";
        yang:delete-supported "false";
        type ciena-6500-types:STRING;
        description
          "Pre-FEC Signal Degrade Threshold Bit Error Rate. Parameter applies when FEC is ON";
        config false;
      }
      leaf otm-term {
        yang:create-supported "false";
        yang:get-supported "true";
        yang:edit-supported "false";
        yang:delete-supported "false";
        type ciena-6500-types:STRING;
        description
          "OTM Termination per layer (OPU and/or ODU and/or OTU)";
        config false;
      }
      leaf ains-time-left {
        yang:create-supported "false";
        yang:get-supported "true";
        yang:edit-supported "false";
        yang:delete-supported "false";
        type ciena-6500-types:TIME;
        description
          "The format will be \"HH-MM\" for the time left in AINS timeout.";
        config false;
      }
      leaf otm-flt-mon {
        yang:create-supported "false";
        yang:get-supported "true";
        yang:edit-supported "false";
        yang:delete-supported "false";
        type ciena-6500-types:STRING;
        description
          "OTM Fault Monitoring per layer (OPU and/or ODU and/or OTU)";
        config false;
      }
      leaf otm-prf-mon {
        yang:create-supported "false";
        yang:get-supported "true";
        yang:edit-supported "false";
        yang:delete-supported "false";
        type ciena-6500-types:STRING;
        description
          "OTM Performance Monitoring per layer (OPU and/or ODU and/or OTU)";
        config false;
      }
      leaf cond-type {
        yang:create-supported "false";
        yang:get-supported "true";
        yang:edit-supported "false";
        yang:delete-supported "false";
        type ciena-6500-enums:OTM_CONDTYPE;
        description
          "The type of conditioning";
        config false;
      }
      leaf dm-count {
        yang:create-supported "false";
        yang:get-supported "true";
        yang:edit-supported "false";
        yang:delete-supported "false";
        type ciena-6500-types:STRING;
        description
          "Most recent delay measurement count.";
        config false;
      }
      leaf hold-off {
        default "0";
        yang:create-supported "false";
        yang:get-supported "true";
        yang:edit-supported "false";
        yang:delete-supported "false";
        type ciena-6500-types:INT;
        description
          "HoldOff signal conditioning timer";
        config false;
      }
      leaf hold-on {
        default "0";
        yang:create-supported "false";
        yang:get-supported "true";
        yang:edit-supported "false";
        yang:delete-supported "false";
        type ciena-6500-types:INT;
        description
          "HoldOn signal conditioning timer";
        config false;
      }
      leaf tx-disp-found {
        yang:create-supported "false";
        yang:get-supported "true";
        yang:edit-supported "false";
        yang:delete-supported "false";
        type union {
          type enumeration {
            enum UNKNOWN;
          }
          type ciena-6500-types:INT;
        }
        description
          "Found the optimum Pre-dispersion compensation from the scanning, ps/nm";
        config false;
      }
      leaf assoc-q {
        yang:create-supported "false";
        yang:get-supported "true";
        yang:edit-supported "false";
        yang:delete-supported "false";
        type union {
          type enumeration {
            enum UNKNOWN;
          }
          type ciena-6500-types:INT;
        }
        description
          "Q associated with the found optimum precomp";
        config false;
      }
      leaf scan {
        yang:create-supported "false";
        yang:get-supported "true";
        yang:edit-supported "false";
        yang:delete-supported "false";
        type enumeration {
          enum START {
            description
              "Triggers Q-based Pre-dispersion compensation Scanning";
          }
          enum STOP {
            description
              "Cancels Q-based Pre-dispersion compensation Scanning";
          }
          enum COMPLETE {
            description
              "Indicates completion of Scanning, only for RTRV ";
          }
        }
        description
          "Q-based Pre-dispersion compensation Scanning";
        config false;
      }
      leaf s-from {
        yang:create-supported "false";
        yang:get-supported "true";
        yang:edit-supported "false";
        yang:delete-supported "false";
        type ciena-6500-types:INT;
        description
          "FROM point of scanning range, ps/nm";
        config false;
      }
      leaf s-to {
        yang:create-supported "false";
        yang:get-supported "true";
        yang:edit-supported "false";
        yang:delete-supported "false";
        type ciena-6500-types:INT;
        description
          "TO point of scanning range, ps/nm";
        config false;
      }
      leaf s-step {
        yang:create-supported "false";
        yang:get-supported "true";
        yang:edit-supported "false";
        yang:delete-supported "false";
        type ciena-6500-types:INT;
        description
          "Compensation optimization scanning step size , ps/nm";
        config false;
      }
      leaf s-dwell {
        yang:create-supported "false";
        yang:get-supported "true";
        yang:edit-supported "false";
        yang:delete-supported "false";
        type ciena-6500-types:INT;
        description
          "Scanning dwell time, second";
        config false;
      }
      leaf tx-freq-min {
        default "0.00";
        yang:create-supported "false";
        yang:get-supported "true";
        yang:edit-supported "false";
        yang:delete-supported "false";
        type ciena-6500-types:STRING;
        description
          "Minimum TX Frequency value in THz (xxx.xxxx)";
        config false;
      }
      leaf tx-freq-max {
        default "0.00";
        yang:create-supported "false";
        yang:get-supported "true";
        yang:edit-supported "false";
        yang:delete-supported "false";
        type ciena-6500-types:STRING;
        description
          "Maximum TX Frequency value in THz (xxx.xxxx)";
        config false;
      }
      leaf rx-enm {
        yang:create-supported "false";
        yang:get-supported "true";
        yang:edit-supported "false";
        yang:delete-supported "false";
        type enumeration {
          enum MODE1 {
            description
              "ENM (Enhanced Non-linear Mitigation) mode 1";
          }
          enum MODE2 {
            description
              "ENM (Enhanced Non-linear Mitigation) mode 2";
          }
          enum UNKNOWN {
            description
              "ENM (Enhanced Non-linear Mitigation) default";
          }
        }
        description
          "Enhanced Non-linear Mitigation mode";
        config false;
      }
      leaf tx-enm {
        yang:create-supported "false";
        yang:get-supported "true";
        yang:edit-supported "false";
        yang:delete-supported "false";
        type enumeration {
          enum MODE1 {
            description
              "ENM (Enhanced Non-linear Mitigation) mode 1";
          }
          enum MODE2 {
            description
              "ENM (Enhanced Non-linear Mitigation) mode 2";
          }
          enum UNKNOWN {
            description
              "ENM (Enhanced Non-linear Mitigation) default";
          }
        }
        description
          "Enhanced Non-linear Mitigation mode";
        config false;
      }
      leaf spli-managed {
        yang:create-supported "false";
        yang:get-supported "true";
        yang:edit-supported "false";
        yang:delete-supported "false";
        type ciena-6500-enums:spliManaged;
        description
          "Identify if Port is Currently Managed by SPLI";
        config false;
      }
      leaf m-aid {
        yang:create-supported "false";
        yang:get-supported "true";
        yang:edit-supported "false";
        yang:delete-supported "false";
        type ciena-6500-types:IDENT;
        description
          "FLEX4 OCLD 2X8QAM300G CP group member line port AID";
        config false;
      }
      leaf odu-rate {
        yang:create-supported "false";
        yang:get-supported "true";
        yang:edit-supported "false";
        yang:delete-supported "false";
        type enumeration {
          enum ODUC2 {
            description
              "ODU layer rate is 2xODU4";
          }
          enum ODUC4 {
            description
              "ODU layer rate is 4xODU4";
          }
        }
        description
          " Number of ODU4s contained by the ODUCn layer in a 8QAM CP group";
        config false;
      }
      leaf prtl-srv {
        yang:create-supported "false";
        yang:get-supported "true";
        yang:edit-supported "false";
        yang:delete-supported "false";
        type enumeration {
          enum ON {
            description
              "Partial survivability is supported";
          }
          enum OFF {
            description
              "Partial survivability is not supported";
          }
        }
        description
          "Indicates partial survivability support";
        config false;
      }
      leaf ochtxsigbw3db {
        yang:create-supported "false";
        yang:get-supported "true";
        yang:edit-supported "false";
        yang:delete-supported "false";
        type ciena-6500-types:STRING;
        description
          "Supported 3dB bandwidth value";
        config false;
      }
      leaf ochtxsigbw10db {
        yang:create-supported "false";
        yang:get-supported "true";
        yang:edit-supported "false";
        yang:delete-supported "false";
        type ciena-6500-types:STRING;
        description
          "Supported 10dB bandwidth value";
        config false;
      }
      leaf ochtxminspecwth {
        yang:create-supported "false";
        yang:get-supported "true";
        yang:edit-supported "false";
        yang:delete-supported "false";
        type ciena-6500-types:STRING;
        description
          "Minimum spectral width";
        config false;
      }
      leaf ochtxfreqres {
        yang:create-supported "false";
        yang:get-supported "true";
        yang:edit-supported "false";
        yang:delete-supported "false";
        type ciena-6500-types:STRING;
        description
          "Supported frequency resolution";
        config false;
      }
      leaf mate-info {
        yang:create-supported "false";
        yang:get-supported "true";
        yang:edit-supported "false";
        yang:delete-supported "false";
        type string {
          length "0..64";
        }
        description
          "Slot and Port info of Mating Peer";
        config false;
      }
      leaf force {
        yang:create-supported "false";
        yang:get-supported "false";
        yang:edit-supported "true";
        yang:delete-supported "false";
        type enumeration {
          enum NO {
            description
              "Do Not Force Edit";
          }
          enum YES {
            description
              "Force Traffic Impacting Edit";
          }
        }
        default "NO";
        description
          "Indicating whether to force a traffic impacting edit to happen";
        config true;
      }
    }
    list sts192c {
      yang:handler "tl1";
      yang:create-supported "false";
      yang:get-supported "true";
      yang:edit-supported "false";
      yang:delete-supported "false";
      key "sts192c";
      config false;
      leaf sts192c {
        mandatory true;
        description
          "AID in format STS192C-shelf-slot-port-sts";
        type ciena-6500-types:aid;
      }
      leaf term {
        yang:get-supported "true";
        type enumeration {
          enum Y {
            description
              "Y=Terminated";
          }
          enum N {
            description
              "N=Not terminated";
          }
        }
        description
          "Y=Terminated/N=Not terminated";
        config false;
      }
      leaf expsglbl {
        yang:get-supported "true";
        type ciena-6500-types:INT;
        description
          "Expected incoming signal label (C2) value";
        config false;
      }
      leaf incsglbl {
        yang:get-supported "true";
        type enumeration {
          enum Y {
            description
              "Display Incoming Signal Label";
          }
          enum N {
            description
              "Exclude Incoming Signal Label";
          }
        }
        description
          "Omit querying the INCSGLBL value to improve retrieve time";
        config false;
      }
      leaf sglbl {
        yang:get-supported "true";
        type ciena-6500-types:INT;
        description
          "Outgoing signal label (C2) value";
        config false;
      }
      leaf trcformat {
        yang:get-supported "true";
        type enumeration {
          enum 16BYTE;
          enum 64BYTE;
        }
        description
          "Path trace format.";
        config false;
      }
      leaf prime {
        yang:get-supported "true";
        type enumeration {
          enum OSS {
            description
              "Operation Support System Owned";
          }
          enum CPS {
            description
              "Control Plane System Owned";
          }
        }
        description
          "The owner of the payload facility";
        config false;
      }
    }
    list ptp {
      yang:handler "tl1";
      yang:create-supported "true";
      yang:get-supported "true";
      yang:edit-supported "true";
      yang:delete-supported "true";
      key "ptp";
      config true;
      leaf ptp {
        mandatory true;
        description
          "AID in format PTP-shelf-slot-port, PTP-shelf-slot-portSsubport, PTP-shelf-slot-portPsubport, PTP-shelf-slotSsubslot-portSsubport, PTP-shelf-slotSsubslot-port, PTP-shelf-slot-ALL, PTP-shelf-ALL, ALL";
        type ciena-6500-types:aid;
      }
      leaf service-type {
        yang:create-supported "true";
        yang:get-supported "true";
        yang:edit-supported "false";
        yang:delete-supported "false";
        type ciena-6500-enums:ptpServiceType;
        description
          "Configured Service Type";
        config true;
      }
      leaf role {
        yang:create-supported "true";
        yang:get-supported "true";
        yang:edit-supported "false";
        yang:delete-supported "false";
        type ciena-6500-enums:PtpRole;
        description
          "Role type in OTUCn-M configuration";
        config true;
      }
      leaf p-aid {
        yang:create-supported "true";
        yang:get-supported "true";
        yang:edit-supported "true";
        yang:delete-supported "false";
        type ciena-6500-types:aid;
        description
          "Specify the Prime PTP AID.";
        config true;
      }
      leaf tx-path-id {
        yang:create-supported "true";
        yang:get-supported "true";
        yang:edit-supported "true";
        yang:delete-supported "false";
        type ciena-6500-types:INT {
          range "1..254";
        }
        description
          "TX path identifier";
        config true;
      }
      leaf cond-type {
        yang:create-supported "true";
        yang:get-supported "true";
        yang:edit-supported "true";
        yang:delete-supported "false";
        type ciena-6500-enums:ptpCondType;
        description
          "The type of Tx conditioning to do in response to certain faults";
        config true;
      }
      leaf tx-pwr {
        yang:create-supported "true";
        yang:get-supported "true";
        yang:edit-supported "true";
        yang:delete-supported "false";
        type ciena-6500-types:STRING;
        description
          "Provisioned TX Power in dBm (xx.x)";
        config true;
      }
      leaf tx-wvlngth-prov {
        default "0.00";
        yang:create-supported "true";
        yang:get-supported "true";
        yang:edit-supported "true";
        yang:delete-supported "false";
        type ciena-6500-types:STRING;
        description
          "Provisioned Wavelength";
        config true;
      }
      leaf differential-encoding {
        yang:create-supported "true";
        yang:get-supported "true";
        yang:edit-supported "true";
        yang:delete-supported "false";
        type enumeration {
          enum NONE {
            description
              "TR Control NONE";
          }
          enum HARD {
            description
              "TR Control HARD";
          }
          enum SOFT {
            description
              "TR Control SOFT";
          }
          enum XD {
            description
              "TR Control XD";
          }
        }
        description
          "OCH Differential Encoding";
        config true;
      }
      leaf tx-spctrl-occp {
        yang:create-supported "true";
        yang:get-supported "true";
        yang:edit-supported "true";
        yang:delete-supported "false";
        type enumeration {
          enum NONE {
            description
              "NONE";
          }
          enum NARROW {
            description
              "NARROW";
          }
          enum WIDE20 {
            description
              "WIDE20";
          }
          enum WIDE25 {
            description
              "WIDE25";
          }
          enum WIDE30 {
            description
              "WIDE30";
          }
          enum WIDE40 {
            description
              "WIDE40";
          }
          enum WIDE50 {
            description
              "WIDE50";
          }
          enum MINSPACE20 {
            description
              "MINSPACE20";
          }
          enum MINSPACE25 {
            description
              "MINSPACE25";
          }
        }
        description
          "OCH Spectral Occupancy setting";
        config true;
      }
      leaf label {
        yang:create-supported "true";
        yang:get-supported "true";
        yang:edit-supported "true";
        yang:delete-supported "false";
        type string {
          length "0..64";
        }
        description
          "User specified Label";
        config true;
      }
      leaf pwr-bal-ctlr {
        yang:create-supported "true";
        yang:get-supported "true";
        yang:edit-supported "true";
        yang:delete-supported "false";
        type enumeration {
          enum DISABLED {
            description
              "Power Balance Controller Disabled";
          }
          enum ENABLED {
            description
              "Power Balance Controller Enabled";
          }
        }
        default "DISABLED";
        description
          "Provisioned Power Balance Controller Operating Mode";
        config true;
      }
      leaf pwr-bal-offset {
        yang:create-supported "true";
        yang:get-supported "true";
        yang:edit-supported "true";
        yang:delete-supported "false";
        type ciena-6500-types:STRING;
        description
          "Provisioned Power Balance Offset in dB (xx.x)";
        config true;
      }
      leaf tuning-mode {
        yang:create-supported "true";
        yang:get-supported "true";
        yang:edit-supported "true";
        yang:delete-supported "false";
        type ciena-6500-enums:ochTuningMode;
        default "UNKNOWN";
        description
          "Provisioned Tuning Mode";
        config true;
      }
      leaf frr {
        yang:create-supported "true";
        yang:get-supported "true";
        yang:edit-supported "true";
        yang:delete-supported "false";
        type enumeration {
          enum DISABLED {
            description
              "DISABLED Mode";
          }
          enum ENABLED {
            description
              "ENABLED Mode";
          }
        }
        default "DISABLED";
        description
          "OCH Fast Receiver Recovery";
        config true;
      }
      leaf frr-config {
        yang:create-supported "true";
        yang:get-supported "true";
        yang:edit-supported "true";
        yang:delete-supported "false";
        type enumeration {
          enum MATCHEDCD {
            description
              "Matched Chromatic Dispersion";
          }
          enum DIVERSECD2 {
            description
              "Diverse Chromatic Dispersion 2 Paths";
          }
        }
        default "MATCHEDCD";
        description
          "OCH FRR Network Configuration";
        config true;
      }
      leaf frr-path1-disp {
        default "AUTO";
        yang:create-supported "true";
        yang:get-supported "true";
        yang:edit-supported "true";
        yang:delete-supported "false";
        type ciena-6500-types:STRING;
        description
          "OCH FRR Link Dispersion for Path 1";
        config true;
      }
      leaf frr-path2-disp {
        default "AUTO";
        yang:create-supported "true";
        yang:get-supported "true";
        yang:edit-supported "true";
        yang:delete-supported "false";
        type ciena-6500-types:STRING;
        description
          "OCH FRR Link Dispersion for Path 2";
        config true;
      }
      leaf optimize-mode {
        yang:create-supported "true";
        yang:get-supported "true";
        yang:edit-supported "true";
        yang:delete-supported "false";
        type ciena-6500-enums:optimizeMode;
        description
          "Performance Optimization Mode";
        config true;
      }
      leaf tx-mode {
        yang:create-supported "true";
        yang:get-supported "true";
        yang:edit-supported "true";
        yang:delete-supported "false";
        type ciena-6500-enums:TxMode;
        description
          "Transmitter Dispersion Mode";
        config true;
      }
      leaf tx-disp-prov {
        yang:create-supported "true";
        yang:get-supported "true";
        yang:edit-supported "true";
        yang:delete-supported "false";
        type ciena-6500-types:STRING;
        description
          "Transmitter Dispersion Value";
        config true;
      }
      leaf path-disp-prov {
        yang:create-supported "true";
        yang:get-supported "true";
        yang:edit-supported "true";
        yang:delete-supported "false";
        type ciena-6500-types:STRING;
        description
          "Path Dispersion Value";
        config true;
      }
      leaf tx-chrip {
        default "AUTO";
        yang:create-supported "true";
        yang:get-supported "true";
        yang:edit-supported "true";
        yang:delete-supported "false";
        type enumeration {
          enum AUTO {
            description
              "Automatic";
          }
          enum POSITIVE {
            description
              "Positive";
          }
          enum NEGATIVE {
            description
              "Negative";
          }
        }
        description
          "Positive or Negative Chirp setting";
        config true;
      }
      leaf enm-prov {
        yang:create-supported "true";
        yang:get-supported "true";
        yang:edit-supported "true";
        yang:delete-supported "false";
        type ciena-6500-enums:ochenm;
        description
          "OCH ENM provisioning mode";
        config true;
      }
      leaf ccda {
        yang:create-supported "true";
        yang:get-supported "true";
        yang:edit-supported "true";
        yang:delete-supported "false";
        type ciena-6500-enums:ccda;
        description
          "TX Channel Contention Detection and Avoidance";
        config true;
      }
      leaf carrier-centering-mode {
        yang:create-supported "true";
        yang:get-supported "true";
        yang:edit-supported "true";
        yang:delete-supported "false";
        type ciena-6500-enums:ochCarrierCenteringMode;
        description
          "Laser centering mode";
        config true;
      }
      leaf tx-wvlngth-spacing {
        yang:create-supported "true";
        yang:get-supported "true";
        yang:edit-supported "true";
        yang:delete-supported "false";
        type ciena-6500-enums:ochTxWvlngthSpacing;
        description
          "OCH Wavelength Spacing, in nm";
        config true;
      }
      leaf tx-freq-prov {
        yang:create-supported "true";
        yang:get-supported "true";
        yang:edit-supported "true";
        yang:delete-supported "false";
        type ciena-6500-types:STRING;
        description
          "Provisioned TX Frequency in THz (xxx.xxxx)";
        config true;
      }
      leaf rotation {
        yang:create-supported "true";
        yang:get-supported "true";
        yang:edit-supported "true";
        yang:delete-supported "false";
        type ciena-6500-enums:rotation;
        description
          "Jones Rotation Setting";
        config true;
      }
      leaf spli-mgmt {
        yang:create-supported "true";
        yang:get-supported "true";
        yang:edit-supported "true";
        yang:delete-supported "false";
        type ciena-6500-enums:spliMgmt;
        default "ON";
        description
          "Identify if Port is Manageable by SPLI";
        config true;
      }
      leaf rx-pwr-thr-prov {
        yang:create-supported "true";
        yang:get-supported "true";
        yang:edit-supported "true";
        yang:delete-supported "false";
        type enumeration {
          enum ON {
            description
              "Use of provisioned thresholds is on";
          }
          enum OFF {
            description
              "Use of provisioned thresholds is off";
          }
        }
        default "OFF";
        description
          "Enable to use provisioned Rx Power thresholds";
        config true;
      }
      leaf rx-pwr-l-thr {
        default "-22.5";
        yang:create-supported "true";
        yang:get-supported "true";
        yang:edit-supported "true";
        yang:delete-supported "false";
        type ciena-6500-types:STRING;
        description
          "Provisioned Rx Power OOR low threshold";
        config true;
      }
      leaf rx-pwr-h-thr {
        default "5.5";
        yang:create-supported "true";
        yang:get-supported "true";
        yang:edit-supported "true";
        yang:delete-supported "false";
        type ciena-6500-types:STRING;
        description
          "Provisioned Rx Power OOR high threshold";
        config true;
      }
      leaf rx-ch-pwr-l-thr {
        default "-18.5";
        yang:create-supported "true";
        yang:get-supported "true";
        yang:edit-supported "true";
        yang:delete-supported "false";
        type ciena-6500-types:STRING;
        description
          "Provisioned Rx channel Power OOR low threshold";
        config true;
      }
      leaf rx-ch-pwr-h-thr {
        default "7";
        yang:create-supported "true";
        yang:get-supported "true";
        yang:edit-supported "true";
        yang:delete-supported "false";
        type ciena-6500-types:STRING;
        description
          "Provisioned Rx channel Power OOR high threshold";
        config true;
      }
      leaf laser-centering-range {
        default "2.5";
        yang:create-supported "true";
        yang:get-supported "true";
        yang:edit-supported "true";
        yang:delete-supported "false";
        type ciena-6500-types:STRING;
        description
          "Sets laser centering range";
        config true;
      }
      leaf och-tx-blanking {
        default "OFF";
        yang:create-supported "true";
        yang:get-supported "true";
        yang:edit-supported "true";
        yang:delete-supported "false";
        type ciena-6500-enums:txb;
        description
          "Manually force the Line port TX power in reduced state.";
        config true;
      }
      leaf ttops {
        default "NO";
        yang:create-supported "true";
        yang:get-supported "true";
        yang:edit-supported "true";
        yang:delete-supported "false";
        type ciena-6500-enums:BOOL_YES_NO;
        description
          "Transponder Triggered Switching Mode Enabled";
        config true;
      }
      leaf fec-frmt {
        yang:create-supported "true";
        yang:get-supported "true";
        yang:edit-supported "true";
        yang:delete-supported "false";
        type ciena-6500-enums:PTP_FECFrmt;
        description
          "Tx/Rx FEC Format";
        config true;
      }
      leaf pre-fec-sf-th-lev {
        default "0.00";
        yang:create-supported "true";
        yang:get-supported "true";
        yang:edit-supported "true";
        yang:delete-supported "false";
        type decimal64 {
          range "-1.00..1.00";
          fraction-digits 2;
        }
        description
          "Pre-FEC Signal Fail Threshold";
        config true;
      }
      leaf pre-fec-sd-th-lev {
        default "0.50";
        yang:create-supported "true";
        yang:get-supported "true";
        yang:edit-supported "true";
        yang:delete-supported "false";
        type decimal64 {
          range "-1.00..3.50";
          fraction-digits 2;
        }
        description
          "Pre-FEC Signal Degrade Threshold";
        config true;
      }
      leaf trans-mode {
        yang:create-supported "true";
        yang:get-supported "true";
        yang:edit-supported "true";
        yang:delete-supported "false";
        type ciena-6500-enums:ptpTransMode;
        description
          "Transmission Mode";
        config true;
      }
      leaf tx-pid {
        default "0";
        yang:create-supported "true";
        yang:get-supported "true";
        yang:edit-supported "true";
        yang:delete-supported "false";
        type ciena-6500-types:INT {
          range "0..7";
        }
        description
          "Tx Physical Layer ID";
        config true;
      }
      leaf tx-gid {
        default "0";
        yang:create-supported "true";
        yang:get-supported "true";
        yang:edit-supported "true";
        yang:delete-supported "false";
        type ciena-6500-types:INT {
          range "0..31";
        }
        description
          "Tx Group ID";
        config true;
      }
      leaf tx-phy-map {
        yang:create-supported "true";
        yang:get-supported "true";
        yang:edit-supported "true";
        yang:delete-supported "false";
        type ciena-6500-types:STRING;
        description
          "Tx Physical Mapping Bitmap";
        config true;
      }
      leaf modem-class {
        yang:create-supported "true";
        yang:get-supported "true";
        yang:edit-supported "true";
        yang:delete-supported "false";
        type ciena-6500-enums:ptpModemClass;
        description
          "Modem Class";
        config true;
      }
      leaf reach-class {
        yang:create-supported "true";
        yang:get-supported "true";
        yang:edit-supported "true";
        yang:delete-supported "false";
        type ciena-6500-enums:ptpReachClass;
        description
          "Reach Class";
        config true;
      }
      leaf linkOpt-mode {
        yang:create-supported "true";
        yang:get-supported "true";
        yang:edit-supported "true";
        yang:delete-supported "false";
        type ciena-6500-enums:ptpLnkOptMode;
        description
          "Link Optimization Mode";
        config true;
      }
      leaf reach-type {
        yang:create-supported "true";
        yang:get-supported "true";
        yang:edit-supported "true";
        yang:delete-supported "false";
        type ciena-6500-enums:ptpReachType;
        description
          "Reach Type";
        config true;
      }
      leaf lnkCustom1 {
        yang:create-supported "true";
        yang:get-supported "true";
        yang:edit-supported "true";
        yang:delete-supported "false";
        type ciena-6500-enums:ptpLnkCustom1;
        description
          "Link Custom1";
        config true;
      }
      leaf lnkCustom2 {
        yang:create-supported "true";
        yang:get-supported "true";
        yang:edit-supported "true";
        yang:delete-supported "false";
        type ciena-6500-enums:ptpLnkCustom2;
        description
          "Link Custom2";
        config true;
      }
      leaf laser-off-mode {
        yang:create-supported "true";
        yang:get-supported "true";
        yang:edit-supported "true";
        yang:delete-supported "false";
        type ciena-6500-enums:ptpLaserOffMode;
        description
          "Laser Off Mode";
        config true;
      }
      leaf laser-freq-thr {
        default "1.6";
        yang:create-supported "true";
        yang:get-supported "true";
        yang:edit-supported "true";
        yang:delete-supported "false";
        type decimal64 {
          range "0.0..3.0";
          fraction-digits 1;
        }
        description
          "Laser Frequency Threshold";
        config true;
      }
      leaf line-build-out {
        default "0";
        yang:create-supported "true";
        yang:get-supported "true";
        yang:edit-supported "true";
        yang:delete-supported "false";
        type ciena-6500-types:INT {
          range "0..5";
        }
        description
          "Line Build Out";
        config true;
      }
      leaf line-cde {
        yang:create-supported "true";
        yang:get-supported "true";
        yang:edit-supported "true";
        yang:delete-supported "false";
        type ciena-6500-enums:ptpLineCde;
        default "AMI";
        description
          "Line Coding";
        config true;
      }
      leaf line-fail {
        yang:create-supported "true";
        yang:get-supported "true";
        yang:edit-supported "true";
        yang:delete-supported "false";
        type ciena-6500-enums:ptpLineFail;
        description
          "Line Fail";
        config true;
      }
      leaf exp-res-time-prov {
        default "10";
        yang:create-supported "true";
        yang:get-supported "true";
        yang:edit-supported "true";
        yang:delete-supported "false";
        type ciena-6500-types:INT {
          range "0..100";
        }
        description
          "Provisioned Acquisition Holdoff Time";
        config true;
      }
      leaf ser-path-disp-min-prov {
        yang:create-supported "true";
        yang:get-supported "true";
        yang:edit-supported "true";
        yang:delete-supported "false";
        type ciena-6500-types:STRING;
        description
          "Provisioned Path Dispersion Minimum for the SEARCH mode";
        config true;
      }
      leaf ser-path-disp-max-prov {
        yang:create-supported "true";
        yang:get-supported "true";
        yang:edit-supported "true";
        yang:delete-supported "false";
        type ciena-6500-types:STRING;
        description
          "Provisioned Path Dispersion Maximum for the SEARCH mode";
        config true;
      }
      leaf laser-status {
        yang:create-supported "true";
        yang:get-supported "true";
        yang:edit-supported "true";
        yang:delete-supported "false";
        type ciena-6500-enums:laserStatus;
        default "ON";
        description
          "Laser status";
        config true;
      }
      leaf lqs-managed {
        yang:create-supported "true";
        yang:get-supported "true";
        yang:edit-supported "true";
        yang:delete-supported "false";
        type ciena-6500-enums:lqsManaged;
        default "NO";
        description
          "Liquid Spectrum managed";
        config true;
      }
      leaf hold-off {
        default "0";
        yang:create-supported "true";
        yang:get-supported "true";
        yang:edit-supported "true";
        yang:delete-supported "false";
        type ciena-6500-types:INT {
          range "0 | 10 | 20..1000";
        }
        description
          "HoldOff signal conditioning timer";
        config true;
      }
      leaf ccda-thr {
        default "-14.0";
        yang:create-supported "true";
        yang:get-supported "true";
        yang:edit-supported "true";
        yang:delete-supported "false";
        type decimal64 {
          range "-30.0..5.0";
          fraction-digits 1;
        }
        description
          "Provisioned CCDA threshold";
        config true;
      }
      leaf optical-sf-rept {
        yang:create-supported "true";
        yang:get-supported "true";
        yang:edit-supported "true";
        yang:delete-supported "false";
        type ciena-6500-enums:opticalSfRept;
        default "OFF";
        description
          "Optical Signal Failed reporting status ";
        config true;
      }
      leaf los-thr {
        default "-35.0";
        yang:create-supported "true";
        yang:get-supported "true";
        yang:edit-supported "true";
        yang:delete-supported "false";
        type decimal64 {
          range "-40.0..5.0";
          fraction-digits 1;
        }
        description
          "loss of signal threshold";
        config true;
      }
      leaf pst {
        yang:create-supported "true";
        yang:get-supported "true";
        yang:edit-supported "false";
        yang:delete-supported "false";
        type enumeration {
          enum IS {
            description
              "In Service(This value can be used in create operation)";
          }
          enum OOS-MA {
            description
              "Out-of-service maintenance for provisioning memory administration(This value can be used in create operation)";
          }
          enum IS-ANR {
            description
              "In Service - Abnormal";
          }
          enum OOS-AU {
            description
              "Out-of-service autonomous from a failure detected point of view. It is not out of service from a state point of view. Alarm is raised if the entity is not able to perform its provisioned functions";
          }
          enum OOS-AUMA {
            description
              "Out-of-service autonomous management - the entity is not able to perform its provisioned functions and is purposefully removed from service";
          }
          enum OOS-MAANR {
            description
              "Out-of-service maintenance - abnormal.";
          }
        }
        description
          "Identify the primary state";
        config true;
      }
      leaf-list sst {
        yang:create-supported "true";
        yang:get-supported "true";
        yang:edit-supported "true";
        yang:delete-supported "false";
        type enumeration {
          enum AINS {
            description
              "Auto-In-Service(This value can be used in create and edit operations)";
          }
          enum AINS-DEA {
            description
              "Auto-In-Service Deactivate(This value can be used in create and edit operations)";
          }
          enum BRIDGED {
            description
              "Transition from switched to bridged";
          }
          enum SWITCHED {
            description
              "Transition from bridged to switched";
          }
          enum ROLL;
          enum ACT;
          enum IDLE;
          enum STBYS;
          enum WRK;
          enum ERRANL;
          enum PSI;
          enum FLT;
          enum MEA;
          enum TSTF;
          enum UEQ;
          enum SGEO;
          enum DISCD;
          enum LPBK;
          enum TS;
          enum FAF;
          enum STBYH;
          enum WRKRX;
          enum WRKTX;
          enum PRTCL;
          enum UAS;
          enum NOSITE;
          enum NOAM;
          enum MON;
          enum MSC;
          enum PROTECTED;
          enum MT {
            description
              "Maintenance(This value can be used in create operation)";
          }
          enum DSBLD;
          enum INHIP;
          enum L2DSBLD;
          enum TSGEN;
          enum TSMON;
          enum TSRECIRC;
          enum TSTIP;
          enum TSTCOMPLD;
          enum TS-DEA;
        }
        description
          "Identify the secondary state";
        config true;
      }
      leaf line-type {
        yang:create-supported "false";
        yang:get-supported "true";
        yang:edit-supported "true";
        yang:delete-supported "false";
        type ciena-6500-enums:linetype;
        description
          "OCH Line Sys Type";
        config true;
      }
      leaf mod {
        yang:create-supported "false";
        yang:get-supported "true";
        yang:edit-supported "true";
        yang:delete-supported "false";
        type ciena-6500-enums:PtpMod;
        description
          "Modulation scheme(Param is applicable only on T-Series shelf.)";
        config true;
      }
      leaf bit-rate {
        yang:create-supported "false";
        yang:get-supported "true";
        yang:edit-supported "false";
        yang:delete-supported "false";
        type ciena-6500-enums:PtpRate;
        description
          "PTP Bit Rate";
        config false;
      }
      leaf baud {
        yang:create-supported "false";
        yang:get-supported "true";
        yang:edit-supported "false";
        yang:delete-supported "false";
        type ciena-6500-enums:ptpBaud;
        description
          "OTSi Symbol rate";
        config false;
      }
      leaf-list m-aid {
        yang:create-supported "false";
        yang:get-supported "true";
        yang:edit-supported "false";
        yang:delete-supported "false";
        type ciena-6500-types:aid;
        description
          "Specify the Member PTP AID List. Format: Member2&Member3&...";
        config false;
      }
      leaf rx-fec-frmt {
        yang:create-supported "false";
        yang:get-supported "true";
        yang:edit-supported "false";
        yang:delete-supported "false";
        type enumeration {
          enum OFF {
            description
              "No FEC";
          }
          enum PFEC {
            description
              "Product FEC";
          }
          enum RS8 {
            description
              "Reed Solomon 8";
          }
          enum SCFEC {
            description
              "Super Concatenated FEC";
          }
          enum UFEC {
            description
              "UFEC";
          }
          enum QFEC {
            description
              "QFEC";
          }
          enum EFEC {
            description
              "EFEC";
          }
          enum LDPCFEC {
            description
              "LDPCFEC";
          }
          enum RS10_KP4 {
            description
              "RS10_KP4";
          }
          enum TFEC {
            description
              "TFEC";
          }
        }
        description
          "Type of Forward Error Correction on RX";
        config false;
      }
      leaf tx-fec-frmt {
        yang:create-supported "false";
        yang:get-supported "true";
        yang:edit-supported "false";
        yang:delete-supported "false";
        type enumeration {
          enum OFF {
            description
              "No FEC";
          }
          enum PFEC {
            description
              "Product FEC";
          }
          enum RS8 {
            description
              "Reed Solomon 8";
          }
          enum SCFEC {
            description
              "Super ConcatenatedFEC";
          }
          enum UFEC {
            description
              "UFEC";
          }
          enum QFEC {
            description
              "QFEC";
          }
          enum EFEC {
            description
              "EFEC";
          }
          enum LDPCFEC {
            description
              "LDPCFEC";
          }
          enum RS10_KP4 {
            description
              "RS10_KP4";
          }
          enum TFEC {
            description
              "TFEC";
          }
        }
        description
          "Type of Forward Error Correction on TX";
        config false;
      }
      leaf-list rx-act-ln-pwr {
        yang:create-supported "false";
        yang:get-supported "true";
        yang:edit-supported "false";
        yang:delete-supported "false";
        type ciena-6500-types:STRING;
        description
          "Lane RX Power in dBm (xx.x) (Format: Lane1|Lane2|...)";
        config false;
      }
      leaf-list tx-act-ln-pwr {
        yang:create-supported "false";
        yang:get-supported "true";
        yang:edit-supported "false";
        yang:delete-supported "false";
        type ciena-6500-types:STRING;
        description
          "Lane TX Power in dBm (xx.x) (Format: Lane1|Lane2|...)";
        config false;
      }
      leaf och-tx-act-power {
        yang:create-supported "false";
        yang:get-supported "true";
        yang:edit-supported "false";
        yang:delete-supported "false";
        type ciena-6500-types:STRING;
        description
          "TX actual power in dBm (xx.x)";
        config false;
      }
      leaf och-tx-min-power {
        yang:create-supported "false";
        yang:get-supported "true";
        yang:edit-supported "false";
        yang:delete-supported "false";
        type ciena-6500-types:STRING;
        description
          "TX minimum power in dBm (xx.x)";
        config false;
      }
      leaf och-tx-max-power {
        yang:create-supported "false";
        yang:get-supported "true";
        yang:edit-supported "false";
        yang:delete-supported "false";
        type ciena-6500-types:STRING;
        description
          "TX maximum power in dBm (xx.x)";
        config false;
      }
      leaf och-rx-act-power {
        yang:create-supported "false";
        yang:get-supported "true";
        yang:edit-supported "false";
        yang:delete-supported "false";
        type ciena-6500-types:STRING;
        description
          "RX actual power in dBm (xx.x)";
        config false;
      }
      leaf och-rx-min-power {
        yang:create-supported "false";
        yang:get-supported "true";
        yang:edit-supported "false";
        yang:delete-supported "false";
        type ciena-6500-types:STRING;
        description
          "RX minimum power in dBm (xx.x)";
        config false;
      }
      leaf och-rx-max-power {
        yang:create-supported "false";
        yang:get-supported "true";
        yang:edit-supported "false";
        yang:delete-supported "false";
        type ciena-6500-types:STRING;
        description
          "RX maximum power in dBm (xx.x)";
        config false;
      }
      leaf och-tx-act-high-power {
        yang:create-supported "false";
        yang:get-supported "true";
        yang:edit-supported "false";
        yang:delete-supported "false";
        type ciena-6500-types:STRING;
        description
          "TX active high power in dBm (xx.x)";
        config false;
      }
      leaf och-tx-act-low-power {
        yang:create-supported "false";
        yang:get-supported "true";
        yang:edit-supported "false";
        yang:delete-supported "false";
        type ciena-6500-types:STRING;
        description
          "TX active low power in dBm (xx.x)";
        config false;
      }
      leaf och-rx-act-high-power {
        yang:create-supported "false";
        yang:get-supported "true";
        yang:edit-supported "false";
        yang:delete-supported "false";
        type ciena-6500-types:STRING;
        description
          "RX active high power in dBm (xx.x)";
        config false;
      }
      leaf och-rx-act-low-power {
        yang:create-supported "false";
        yang:get-supported "true";
        yang:edit-supported "false";
        yang:delete-supported "false";
        type ciena-6500-types:STRING;
        description
          "RX active low power in dBm (xx.x)";
        config false;
      }
      leaf tx-wvlngth-min {
        default "0.00";
        yang:create-supported "false";
        yang:get-supported "true";
        yang:edit-supported "false";
        yang:delete-supported "false";
        type ciena-6500-types:STRING;
        description
          "Minimum Wavelength Range";
        config false;
      }
      leaf tx-wvlngth-max {
        default "0.00";
        yang:create-supported "false";
        yang:get-supported "true";
        yang:edit-supported "false";
        yang:delete-supported "false";
        type ciena-6500-types:STRING;
        description
          "Maximum Wavelength Range";
        config false;
      }
      leaf och-rx-ch-act-power {
        yang:create-supported "false";
        yang:get-supported "true";
        yang:edit-supported "false";
        yang:delete-supported "false";
        type ciena-6500-types:STRING;
        description
          "RX channel actual power in dBm (xx.x)";
        config false;
      }
      leaf och-rx-ch-min-power {
        yang:create-supported "false";
        yang:get-supported "true";
        yang:edit-supported "false";
        yang:delete-supported "false";
        type ciena-6500-types:STRING;
        description
          "RX channel minimum power in dBm (xx.x)";
        config false;
      }
      leaf och-rx-ch-max-power {
        yang:create-supported "false";
        yang:get-supported "true";
        yang:edit-supported "false";
        yang:delete-supported "false";
        type ciena-6500-types:STRING;
        description
          "RX channel maximum power in dBm (xx.x)";
        config false;
      }
      leaf och-rx-echo-trace {
        yang:create-supported "false";
        yang:get-supported "true";
        yang:edit-supported "false";
        yang:delete-supported "false";
        type ciena-6500-types:STRING;
        description
          "TR Transmit Identifier Received";
        config false;
      }
      leaf och-tx-trace {
        yang:create-supported "false";
        yang:get-supported "true";
        yang:edit-supported "false";
        yang:delete-supported "false";
        type ciena-6500-types:STRING;
        description
          "TR Transmit Identifier Received Expected";
        config false;
      }
      leaf och-tx-assoc-far-end-rx {
        yang:create-supported "false";
        yang:get-supported "true";
        yang:edit-supported "false";
        yang:delete-supported "false";
        type ciena-6500-types:STRING;
        description
          "Transmitter associated far end receiver";
        config false;
      }
      leaf och-max-pmd {
        yang:create-supported "false";
        yang:get-supported "true";
        yang:edit-supported "false";
        yang:delete-supported "false";
        type ciena-6500-types:STRING;
        description
          "Supported Mean DGD (Differential Group Delay) value";
        config false;
      }
      leaf och-rx-act-pmd {
        yang:create-supported "false";
        yang:get-supported "true";
        yang:edit-supported "false";
        yang:delete-supported "false";
        type ciena-6500-types:STRING;
        description
          "Estimated Instance of DGD (Differential Group Delay) value";
        config false;
      }
      leaf est-length {
        yang:create-supported "false";
        yang:get-supported "true";
        yang:edit-supported "false";
        yang:delete-supported "false";
        type ciena-6500-types:STRING;
        description
          "Estimated fiber length";
        config false;
      }
      leaf laser-bias-end-of-life {
        yang:create-supported "false";
        yang:get-supported "true";
        yang:edit-supported "false";
        yang:delete-supported "false";
        type ciena-6500-types:STRING;
        description
          "Laser Bias Current.";
        config false;
      }
      leaf rtd {
        yang:create-supported "false";
        yang:get-supported "true";
        yang:edit-supported "false";
        yang:delete-supported "false";
        type ciena-6500-types:STRING;
        description
          "OCH Round Trip Delay.";
        config false;
      }
      leaf uni-latency {
        yang:create-supported "false";
        yang:get-supported "true";
        yang:edit-supported "false";
        yang:delete-supported "false";
        type ciena-6500-types:STRING;
        description
          "OCH Unidirectional Latency.";
        config false;
      }
      leaf ains-time-left {
        yang:create-supported "false";
        yang:get-supported "true";
        yang:edit-supported "false";
        yang:delete-supported "false";
        type ciena-6500-types:TIME;
        description
          "The format will be \"HH-MM\" for the time left in AINS timeout.";
        config false;
      }
      leaf pwr-bal-act-offset {
        yang:create-supported "false";
        yang:get-supported "true";
        yang:edit-supported "false";
        yang:delete-supported "false";
        type ciena-6500-types:STRING;
        description
          "Provisioned Power Balance Actual Offset in dB (xx.x)";
        config false;
      }
      leaf och-tx-act-disp {
        yang:create-supported "false";
        yang:get-supported "true";
        yang:edit-supported "false";
        yang:delete-supported "false";
        type ciena-6500-types:STRING;
        description
          "Transmitter total actual link dispersion in the near-to-far direction";
        config false;
      }
      leaf tx-disp-min {
        yang:create-supported "false";
        yang:get-supported "true";
        yang:edit-supported "false";
        yang:delete-supported "false";
        type ciena-6500-types:STRING;
        description
          "Minimum Transmitter Dispersion Value";
        config false;
      }
      leaf tx-disp-max {
        yang:create-supported "false";
        yang:get-supported "true";
        yang:edit-supported "false";
        yang:delete-supported "false";
        type ciena-6500-types:STRING;
        description
          "Maximum Transmitter Dispersion Value";
        config false;
      }
      leaf och-rx-act-disp {
        yang:create-supported "false";
        yang:get-supported "true";
        yang:edit-supported "false";
        yang:delete-supported "false";
        type ciena-6500-types:STRING;
        description
          "Receiver total actual link dispersion in the far-to-near direction";
        config false;
      }
      leaf och-tx-pre-disp {
        yang:create-supported "false";
        yang:get-supported "true";
        yang:edit-supported "false";
        yang:delete-supported "false";
        type ciena-6500-types:STRING;
        description
          "Tx Precompensation Dispersion Value.";
        config false;
      }
      leaf och-rx-post-disp {
        yang:create-supported "false";
        yang:get-supported "true";
        yang:edit-supported "false";
        yang:delete-supported "false";
        type ciena-6500-types:STRING;
        description
          "Rx Postcompensation Dispersion Value.";
        config false;
      }
      leaf reach-spec {
        yang:create-supported "false";
        yang:get-supported "true";
        yang:edit-supported "false";
        yang:delete-supported "false";
        type ciena-6500-types:STRING;
        description
          "Reach Specification";
        config false;
      }
      leaf tx-freq-min {
        default "0.00";
        yang:create-supported "false";
        yang:get-supported "true";
        yang:edit-supported "false";
        yang:delete-supported "false";
        type ciena-6500-types:STRING;
        description
          "Minimum TX Frequency value in THz (xxx.xxxx)";
        config false;
      }
      leaf tx-freq-max {
        default "0.00";
        yang:create-supported "false";
        yang:get-supported "true";
        yang:edit-supported "false";
        yang:delete-supported "false";
        type ciena-6500-types:STRING;
        description
          "Maximum TX Frequency value in THz (xxx.xxxx)";
        config false;
      }
      leaf tx-disp-found {
        yang:create-supported "false";
        yang:get-supported "true";
        yang:edit-supported "false";
        yang:delete-supported "false";
        type ciena-6500-types:STRING;
        description
          "Found the optimum Pre-dispersion compensation from the scanning, ps/nm";
        config false;
      }
      leaf assoc-q {
        yang:create-supported "false";
        yang:get-supported "true";
        yang:edit-supported "false";
        yang:delete-supported "false";
        type ciena-6500-types:STRING;
        description
          "Q associated with the found optimum precomp";
        config false;
      }
      leaf scan {
        yang:create-supported "false";
        yang:get-supported "true";
        yang:edit-supported "false";
        yang:delete-supported "false";
        type ciena-6500-enums:ScanState;
        description
          "Q-based Pre-dispersion compensation Scanning";
        config false;
      }
      leaf s-from {
        yang:create-supported "false";
        yang:get-supported "true";
        yang:edit-supported "false";
        yang:delete-supported "false";
        type ciena-6500-types:STRING;
        description
          "FROM point of scanning range, ps/nm";
        config false;
      }
      leaf s-to {
        yang:create-supported "false";
        yang:get-supported "true";
        yang:edit-supported "false";
        yang:delete-supported "false";
        type ciena-6500-types:STRING;
        description
          "TO point of scanning range, ps/nm";
        config false;
      }
      leaf s-step {
        yang:create-supported "false";
        yang:get-supported "true";
        yang:edit-supported "false";
        yang:delete-supported "false";
        type ciena-6500-types:STRING;
        description
          "Compensation optimization scanning step size , ps/nm";
        config false;
      }
      leaf s-dwell {
        yang:create-supported "false";
        yang:get-supported "true";
        yang:edit-supported "false";
        yang:delete-supported "false";
        type ciena-6500-types:STRING;
        description
          "Scanning dwell time, second";
        config false;
      }
      leaf spli-managed {
        yang:create-supported "false";
        yang:get-supported "true";
        yang:edit-supported "false";
        yang:delete-supported "false";
        type ciena-6500-enums:spliManaged;
        description
          "Identify if Port is Currently Managed by SPLI";
        config false;
      }
      leaf och-tx-sig-bw-3db {
        default "35.0";
        yang:create-supported "false";
        yang:get-supported "true";
        yang:edit-supported "false";
        yang:delete-supported "false";
        type ciena-6500-types:STRING;
        description
          "Supported 3dB bandwidth value";
        config false;
      }
      leaf och-tx-sig-bw-10db {
        default "38.6";
        yang:create-supported "false";
        yang:get-supported "true";
        yang:edit-supported "false";
        yang:delete-supported "false";
        type ciena-6500-types:STRING;
        description
          "Supported 10dB bandwidth value";
        config false;
      }
      leaf och-tx-min-spec-width {
        default "37.5";
        yang:create-supported "false";
        yang:get-supported "true";
        yang:edit-supported "false";
        yang:delete-supported "false";
        type ciena-6500-types:STRING;
        description
          "Minimum spectral width";
        config false;
      }
      leaf och-tx-freqr-es {
        default "0.1";
        yang:create-supported "false";
        yang:get-supported "true";
        yang:edit-supported "false";
        yang:delete-supported "false";
        type ciena-6500-types:STRING;
        description
          "Supported frequency resolution";
        config false;
      }
      leaf act_trans-mode {
        yang:create-supported "false";
        yang:get-supported "true";
        yang:edit-supported "false";
        yang:delete-supported "false";
        type ciena-6500-enums:ptpTransMode;
        description
          "Actual Transmission Mode";
        config false;
      }
      leaf pre-fec-sf-th-ber {
        default "0.0";
        yang:create-supported "false";
        yang:get-supported "true";
        yang:edit-supported "false";
        yang:delete-supported "false";
        type ciena-6500-types:STRING;
        description
          "The corresponding BER for a given Pre-FEC SF Threshold setting in dDQ";
        config false;
      }
      leaf pre-fec-sd-th-ber {
        default "0.0";
        yang:create-supported "false";
        yang:get-supported "true";
        yang:edit-supported "false";
        yang:delete-supported "false";
        type ciena-6500-types:STRING;
        description
          "The corresponding BER for a given Pre-FEC SD Threshold setting in dDQ";
        config false;
      }
      leaf rx-pid {
        default "0";
        yang:create-supported "false";
        yang:get-supported "true";
        yang:edit-supported "false";
        yang:delete-supported "false";
        type union {
          type enumeration {
            enum UNKNOWN;
          }
          type ciena-6500-types:INT {
            range "0..7";
          }
        }
        description
          "Rx Physical Layer ID";
        config false;
      }
      leaf rx-gid {
        default "0";
        yang:create-supported "false";
        yang:get-supported "true";
        yang:edit-supported "false";
        yang:delete-supported "false";
        type union {
          type enumeration {
            enum UNKNOWN;
          }
          type ciena-6500-types:INT {
            range "0..31";
          }
        }
        description
          "Rx Group ID";
        config false;
      }
      leaf rx-phy-map {
        yang:create-supported "false";
        yang:get-supported "true";
        yang:edit-supported "false";
        yang:delete-supported "false";
        type ciena-6500-types:STRING;
        description
          "Rx Physical Mapping Bitmap";
        config false;
      }
      leaf allocated-spec-width {
        yang:create-supported "false";
        yang:get-supported "true";
        yang:edit-supported "false";
        yang:delete-supported "false";
        type ciena-6500-types:STRING;
        description
          "Allocated Spectral Width";
        config false;
      }
      leaf rx-mon {
        yang:create-supported "false";
        yang:get-supported "true";
        yang:edit-supported "false";
        yang:delete-supported "false";
        type enumeration {
          enum YES;
          enum NO;
        }
        description
          "Indicate if the signal is monitored in the Rx direction for alarms and PMs and OMs.";
        config false;
      }
      leaf rx-term {
        yang:create-supported "false";
        yang:get-supported "true";
        yang:edit-supported "false";
        yang:delete-supported "false";
        type enumeration {
          enum YES;
          enum NO;
        }
        description
          "Indicate if the signal is terminated in the Rx direction or not.";
        config false;
      }
      leaf rqst-trans-mode {
        yang:create-supported "false";
        yang:get-supported "true";
        yang:edit-supported "false";
        yang:delete-supported "false";
        type ciena-6500-enums:ptpTransMode;
        description
          "Requested Transmission Mode";
        config false;
      }
      leaf saved-trans-mode {
        yang:create-supported "false";
        yang:get-supported "true";
        yang:edit-supported "false";
        yang:delete-supported "false";
        type ciena-6500-enums:ptpTransMode;
        description
          "Saved Actual Applied Transmission Mode";
        config false;
      }
      leaf rqst-linkOpt-mode {
        yang:create-supported "false";
        yang:get-supported "true";
        yang:edit-supported "false";
        yang:delete-supported "false";
        type ciena-6500-enums:ptpLnkOptMode;
        description
          "Requested Link Optimization Mode";
        config false;
      }
      leaf act-linkOpt-mode {
        yang:create-supported "false";
        yang:get-supported "true";
        yang:edit-supported "false";
        yang:delete-supported "false";
        type ciena-6500-enums:ptpLnkOptMode;
        description
          "Actual Applied Link Optimization Mode";
        config false;
      }
      leaf saved-linkOpt-mode {
        yang:create-supported "false";
        yang:get-supported "true";
        yang:edit-supported "false";
        yang:delete-supported "false";
        type ciena-6500-enums:ptpLnkOptMode;
        description
          "Saved Actual Applied Link Optimization Mode";
        config false;
      }
      leaf rqst-tx-wvlngth {
        yang:create-supported "false";
        yang:get-supported "true";
        yang:edit-supported "false";
        yang:delete-supported "false";
        type ciena-6500-types:STRING;
        description
          "Requested Wavelength";
        config false;
      }
      leaf act-tx-wvlngth {
        yang:create-supported "false";
        yang:get-supported "true";
        yang:edit-supported "false";
        yang:delete-supported "false";
        type ciena-6500-types:STRING;
        description
          "Actual Applied Wavelength";
        config false;
      }
      leaf rqst-tx-wvlngth-spacing {
        yang:create-supported "false";
        yang:get-supported "true";
        yang:edit-supported "false";
        yang:delete-supported "false";
        type ciena-6500-enums:ochTxWvlngthSpacing;
        description
          "Requested Wavelength Spacing, in nm";
        config false;
      }
      leaf rqst-tx-freq {
        yang:create-supported "false";
        yang:get-supported "true";
        yang:edit-supported "false";
        yang:delete-supported "false";
        type ciena-6500-types:STRING;
        description
          "Requested TX Frequency in THz (xxx.xxxx)";
        config false;
      }
      leaf act-tx-freq {
        yang:create-supported "false";
        yang:get-supported "true";
        yang:edit-supported "false";
        yang:delete-supported "false";
        type ciena-6500-types:STRING;
        description
          "Actual Applied TX Frequency in THz (xxx.xxxx)";
        config false;
      }
      leaf rqst-tx-pwr {
        yang:create-supported "false";
        yang:get-supported "true";
        yang:edit-supported "false";
        yang:delete-supported "false";
        type ciena-6500-types:STRING;
        description
          "Requested TX Power in dBm (xx.x)";
        config false;
      }
      leaf rqst-tx-mode {
        yang:create-supported "false";
        yang:get-supported "true";
        yang:edit-supported "false";
        yang:delete-supported "false";
        type ciena-6500-enums:TxMode;
        description
          "Requested Transmitter Dispersion Mode";
        config false;
      }
      leaf act-tx-mode {
        yang:create-supported "false";
        yang:get-supported "true";
        yang:edit-supported "false";
        yang:delete-supported "false";
        type ciena-6500-enums:TxMode;
        description
          "Actual Applied Transmitter Dispersion Mode";
        config false;
      }
      leaf rqst-tx-disp {
        yang:create-supported "false";
        yang:get-supported "true";
        yang:edit-supported "false";
        yang:delete-supported "false";
        type ciena-6500-types:STRING;
        description
          "Requested Transmitter Dispersion Value";
        config false;
      }
      leaf act-tx-disp {
        yang:create-supported "false";
        yang:get-supported "true";
        yang:edit-supported "false";
        yang:delete-supported "false";
        type ciena-6500-types:STRING;
        description
          "Actual Applied Transmitter Dispersion Value";
        config false;
      }
      leaf rqst-path-disp {
        yang:create-supported "false";
        yang:get-supported "true";
        yang:edit-supported "false";
        yang:delete-supported "false";
        type ciena-6500-types:STRING;
        description
          "Requested Path Dispersion Value";
        config false;
      }
      leaf act-path-disp {
        yang:create-supported "false";
        yang:get-supported "true";
        yang:edit-supported "false";
        yang:delete-supported "false";
        type ciena-6500-types:STRING;
        description
          "Actual Applied Path Dispersion Value";
        config false;
      }
      leaf rqst-carrier-centering-mode {
        yang:create-supported "false";
        yang:get-supported "true";
        yang:edit-supported "false";
        yang:delete-supported "false";
        type ciena-6500-enums:ochCarrierCenteringMode;
        description
          "Requested Laser centering mode";
        config false;
      }
      leaf act-carrier-centering-mode {
        yang:create-supported "false";
        yang:get-supported "true";
        yang:edit-supported "false";
        yang:delete-supported "false";
        type ciena-6500-enums:ochCarrierCenteringMode;
        description
          "Actual Applied Laser centering mode";
        config false;
      }
      leaf rqst-laser-centering-range {
        yang:create-supported "false";
        yang:get-supported "true";
        yang:edit-supported "false";
        yang:delete-supported "false";
        type ciena-6500-types:STRING;
        description
          "Requested laser centering range";
        config false;
      }
      leaf act-laser-centering-range {
        yang:create-supported "false";
        yang:get-supported "true";
        yang:edit-supported "false";
        yang:delete-supported "false";
        type ciena-6500-types:STRING;
        description
          "Actual Applied laser centering range";
        config false;
      }
      leaf rqst-ccda {
        yang:create-supported "false";
        yang:get-supported "true";
        yang:edit-supported "false";
        yang:delete-supported "false";
        type ciena-6500-enums:ccda;
        description
          "Requested Channel Contention Detection and Avoidance";
        config false;
      }
      leaf act-ccda {
        yang:create-supported "false";
        yang:get-supported "true";
        yang:edit-supported "false";
        yang:delete-supported "false";
        type ciena-6500-enums:ccda;
        description
          "Actual Applied Channel Contention Detection and Avoidance";
        config false;
      }
      leaf rqst-och-tx-blanking {
        yang:create-supported "false";
        yang:get-supported "true";
        yang:edit-supported "false";
        yang:delete-supported "false";
        type ciena-6500-enums:txb;
        description
          "Requested TX power in reduced state.";
        config false;
      }
      leaf act-och-tx-blanking {
        yang:create-supported "false";
        yang:get-supported "true";
        yang:edit-supported "false";
        yang:delete-supported "false";
        type ciena-6500-enums:txb;
        description
          "Actual Applied TX power in reduced state.";
        config false;
      }
      leaf rqst-line-type {
        yang:create-supported "false";
        yang:get-supported "true";
        yang:edit-supported "false";
        yang:delete-supported "false";
        type ciena-6500-enums:linetype;
        description
          "Requested Line Sys Type";
        config false;
      }
      leaf rqst-allocated-spec-width {
        yang:create-supported "false";
        yang:get-supported "true";
        yang:edit-supported "false";
        yang:delete-supported "false";
        type ciena-6500-types:STRING;
        description
          "Requested Allocated Spectral Width";
        config false;
      }
      leaf rqst-exp-res-time {
        yang:create-supported "false";
        yang:get-supported "true";
        yang:edit-supported "false";
        yang:delete-supported "false";
        type union {
          type enumeration {
            enum UNKNOWN;
          }
          type ciena-6500-types:INT {
            range "0..100";
          }
        }
        description
          "Requested Acquisition Holdoff Time";
        config false;
      }
      leaf act-exp-res-time {
        yang:create-supported "false";
        yang:get-supported "true";
        yang:edit-supported "false";
        yang:delete-supported "false";
        type union {
          type enumeration {
            enum UNKNOWN;
          }
          type ciena-6500-types:INT {
            range "0..100";
          }
        }
        description
          "Actual Applied Acquisition Holdoff Time";
        config false;
      }
      leaf rqst-tuning-mode {
        yang:create-supported "false";
        yang:get-supported "true";
        yang:edit-supported "false";
        yang:delete-supported "false";
        type ciena-6500-enums:ochTuningMode;
        description
          "Requested Tuning Mode";
        config false;
      }
      leaf act-tuning-mode {
        yang:create-supported "false";
        yang:get-supported "true";
        yang:edit-supported "false";
        yang:delete-supported "false";
        type ciena-6500-enums:ochTuningMode;
        description
          "Activated Tuning Mode";
        config false;
      }
      leaf mate-info {
        yang:create-supported "false";
        yang:get-supported "true";
        yang:edit-supported "false";
        yang:delete-supported "false";
        type string {
          length "0..64";
        }
        description
          "";
        config false;
      }
      leaf rqst-lqs-managed {
        yang:create-supported "false";
        yang:get-supported "true";
        yang:edit-supported "false";
        yang:delete-supported "false";
        type ciena-6500-enums:lqsManaged;
        description
          "Requested Liquid Spectrum managed";
        config false;
      }
      leaf laser-tuned {
        yang:create-supported "false";
        yang:get-supported "true";
        yang:edit-supported "false";
        yang:delete-supported "false";
        type ciena-6500-enums:lasertuned;
        description
          "Laser tuning status";
        config false;
      }
      leaf said {
        yang:create-supported "false";
        yang:get-supported "true";
        yang:edit-supported "false";
        yang:delete-supported "false";
        type ciena-6500-types:aid;
        description
          "Specify the Service ODUCTP AID for Mate to Mate Interconnection";
        config false;
      }
      leaf force {
        yang:create-supported "false";
        yang:get-supported "false";
        yang:edit-supported "true";
        yang:delete-supported "false";
        type enumeration {
          enum NO {
            description
              "Do Not Force Edit";
          }
          enum YES {
            description
              "Force Traffic Impacting Edit";
          }
        }
        default "NO";
        description
          "Indicating whether to force an edit when facility still in service (traffic impacting)";
        config true;
      }
    }
    list otuttp {
      yang:handler "tl1";
      yang:create-supported "true";
      yang:get-supported "true";
      yang:edit-supported "true";
      yang:delete-supported "true";
      key "otu";
      config true;
      leaf otu {
        mandatory true;
        description
          "AID in format OTUTTP-shelf-slot-port, OTUTTP-shelf-slot-portSsubport, OTUTTP-shelf-slot-portPsubport, OTUTTP-shelf-slotSsubslot-port, OTUTTP-shelf-slotSsubslot-portSsubport, OTUTTP-shelf-slot-ALL, OTUTTP-shelf-ALL, ALL";
        type ciena-6500-types:aid;
      }
      leaf label {
        yang:create-supported "true";
        yang:get-supported "true";
        yang:edit-supported "true";
        yang:delete-supported "false";
        type string {
          length "0..64";
        }
        description
          "User specified Label";
        config true;
      }
      leaf rout-sig-disabled {
        yang:create-supported "true";
        yang:get-supported "true";
        yang:edit-supported "true";
        yang:delete-supported "false";
        type enumeration {
          enum NO {
            description
              "Routing signalling enabled. The OSRP will have control over the ODUs created under this TTP and no user created ODU will be allowed.";
          }
          enum YES {
            description
              "Routing signalling disabled";
          }
        }
        default "NO";
        description
          "Specifies whether Routing Signalling is disabled on this TTP.";
        config true;
      }
      leaf rx-fec-frmt {
        yang:create-supported "true";
        yang:get-supported "true";
        yang:edit-supported "true";
        yang:delete-supported "false";
        type ciena-6500-enums:OTU_FECFrmt;
        description
          "Type of Forward Error Correction on RX";
        config true;
      }
      leaf tx-fec-frmt {
        yang:create-supported "true";
        yang:get-supported "true";
        yang:edit-supported "true";
        yang:delete-supported "false";
        type ciena-6500-enums:OTU_FECFrmt;
        description
          "Type of Forward Error Correction on TX";
        config true;
      }
      leaf oper-chg-evt {
        yang:create-supported "true";
        yang:get-supported "true";
        yang:edit-supported "true";
        yang:delete-supported "false";
        type enumeration {
          enum ON {
            description
              "Enable OTU Operator Specific TTI Change event";
          }
          enum OFF {
            description
              "Disable OTU Operator Specific TTI Change event";
          }
        }
        default "OFF";
        description
          "To enable or disable OTU Operator Specific TTI Change events";
        config true;
      }
      leaf sapi-chg-evt {
        yang:create-supported "true";
        yang:get-supported "true";
        yang:edit-supported "true";
        yang:delete-supported "false";
        type enumeration {
          enum ON {
            description
              "Enable OTU SAPI Specific TTI Change event";
          }
          enum OFF {
            description
              "Disable OTU SAPI Specific TTI Change event";
          }
        }
        default "OFF";
        description
          "To enable or disable OTU SAPI Specific TTI Change events";
        config true;
      }
      leaf dapi-chg-evt {
        yang:create-supported "true";
        yang:get-supported "true";
        yang:edit-supported "true";
        yang:delete-supported "false";
        type enumeration {
          enum ON {
            description
              "Enable OTU DAPI Specific TTI Change event";
          }
          enum OFF {
            description
              "Disable OTU DAPI Specific TTI Change event";
          }
        }
        default "OFF";
        description
          "To enable or disable OTU DAPI Specific TTI Change events";
        config true;
      }
      leaf tx-sapi {
        yang:create-supported "true";
        yang:get-supported "true";
        yang:edit-supported "true";
        yang:delete-supported "false";
        type string {
          length "0..15";
        }
        description
          "The Source Access Point Identifier (SAPI), provisioned by the managing system at the termination source, to be placed in the Trail Trace Identifier (TTI) overhead position of the source of a trail.";
        config true;
      }
      leaf tx-dapi {
        yang:create-supported "true";
        yang:get-supported "true";
        yang:edit-supported "true";
        yang:delete-supported "false";
        type string {
          length "0..15";
        }
        description
          "The Destination Access Point Identifier (DAPI), provisioned by the managing system at the termination source, to be placed in the Trail Trace Identifier (TTI) overhead position of the source of a trail.";
        config true;
      }
      leaf tx-oper {
        yang:create-supported "true";
        yang:get-supported "true";
        yang:edit-supported "true";
        yang:delete-supported "false";
        type string {
          length "0..32";
        }
        description
          "The operator specific part of the Trail Trace Identifier (TTI) information, provisioned by the managing system at the termination source, to be placed in the TTI overhead position of the source of a trail.";
        config true;
      }
      leaf ex-sapi {
        yang:create-supported "true";
        yang:get-supported "true";
        yang:edit-supported "true";
        yang:delete-supported "false";
        type string {
          length "0..15";
        }
        description
          "The expected Source Access Point Identifier (SAPI), provisioned by the managing system, to be compared with the received SAPI at the overhead position of the sink for the purpose of checking the integrity of connectivity. ";
        config true;
      }
      leaf ex-dapi {
        yang:create-supported "true";
        yang:get-supported "true";
        yang:edit-supported "true";
        yang:delete-supported "false";
        type string {
          length "0..15";
        }
        description
          "The expected Destination Access Point Identifier (DAPI), provisioned by the managing system, to be compared with the received DAPI at the overhead position of the sink for the purpose of checking the integrity of connectivity. ";
        config true;
      }
      leaf ex-oper {
        yang:create-supported "true";
        yang:get-supported "true";
        yang:edit-supported "true";
        yang:delete-supported "false";
        type string {
          length "0..32";
        }
        description
          "The expected operator specific part of the Trail Trace Identifier (TTI) information, provisioned by the managing system at the termination source, to be placed in the TTI overhead position of the source of a trail.";
        config true;
      }
      leaf tf-mode {
        yang:create-supported "true";
        yang:get-supported "true";
        yang:edit-supported "true";
        yang:delete-supported "false";
        type ciena-6500-enums:otntfMode;
        default "OFF";
        description
          "Trace Fail Mode";
        config true;
      }
      leaf tim-enable {
        yang:create-supported "true";
        yang:get-supported "true";
        yang:edit-supported "true";
        yang:delete-supported "false";
        type ciena-6500-enums:TIMEN;
        description
          "The Trail Trace Identifier Mismatch (TIM) controls checking for Trace Identifier Mismatch fault detection. ";
        config true;
      }
      leaf pre-fec-sf-th-lev {
        yang:create-supported "true";
        yang:get-supported "true";
        yang:edit-supported "true";
        yang:delete-supported "false";
        type ciena-6500-types:STRING;
        description
          "Pre-FEC Signal Fail Threshold Level. Parameter applies when FEC is ON";
        config true;
      }
      leaf pre-fec-sd-th-lev {
        yang:create-supported "true";
        yang:get-supported "true";
        yang:edit-supported "true";
        yang:delete-supported "false";
        type ciena-6500-types:STRING;
        description
          "Pre-FEC Signal Degrade Threshold Level. Parameter applies when FEC is ON";
        config true;
      }
      leaf otu-sd-th-lev {
        default "6";
        yang:create-supported "true";
        yang:get-supported "true";
        yang:edit-supported "true";
        yang:delete-supported "false";
        type ciena-6500-types:INT {
          range "6..9";
        }
        description
          "OTU Signal Degrade Threshold Level";
        config true;
      }
      leaf hold-off {
        default "0";
        yang:create-supported "true";
        yang:get-supported "true";
        yang:edit-supported "true";
        yang:delete-supported "false";
        type ciena-6500-types:INT {
          range "0 | 10 | 20..1000";
        }
        description
          "HoldOff signal conditioning timer";
        config true;
      }
      leaf hold-on {
        default "0";
        yang:create-supported "true";
        yang:get-supported "true";
        yang:edit-supported "true";
        yang:delete-supported "false";
        type ciena-6500-types:INT {
          range "0 | 2 | 4..500";
        }
        description
          "HoldOn signal conditioning timer";
        config true;
      }
      leaf rate {
        yang:create-supported "true";
        yang:get-supported "true";
        yang:edit-supported "true";
        yang:delete-supported "false";
        type ciena-6500-enums:OtuRate;
        description
          "OTUCn Rate";
        config true;
      }
      leaf num-ts {
        default "1";
        yang:create-supported "true";
        yang:get-supported "true";
        yang:edit-supported "true";
        yang:delete-supported "false";
        type ciena-6500-types:INT {
          range "1..320";
        }
        description
          "Used to identify the number of tributaries comprising this TTP. For on OTN TTP, this can change based on potential configuration of desired payload type (e.g. for ODU1 with OPVC payload, this value is 16; with CBR it is 1).";
        config true;
      }
      leaf otu-oh-non-term {
        yang:create-supported "true";
        yang:get-supported "true";
        yang:edit-supported "true";
        yang:delete-supported "false";
        type enumeration {
          enum NONE {
            description
              "Entire GCC OH terminated";
          }
          enum GCC0 {
            description
              "GCC0 portion of OTU OH not terminated";
          }
          enum GCC0MODE1 {
            description
              "GCC0MODE1 portion of OTU OH not terminated";
          }
        }
        description
          "Indicating whether to terminate GCC OH or not";
        config true;
      }
      leaf degm-intv {
        default "2";
        yang:create-supported "true";
        yang:get-supported "true";
        yang:edit-supported "true";
        yang:delete-supported "false";
        type ciena-6500-types:INT {
          range "2..10";
        }
        description
          "Consecutive bad intervals required to declare signal degrade";
        config true;
      }
      leaf degthr-percentage {
        default "100";
        yang:create-supported "true";
        yang:get-supported "true";
        yang:edit-supported "true";
        yang:delete-supported "false";
        type ciena-6500-types:INT {
          range "1..1000";
        }
        description
          "Percentage of errored blocks required to declare an interval bad";
        config true;
      }
      leaf supported-term-pt {
        yang:create-supported "true";
        yang:get-supported "true";
        yang:edit-supported "true";
        yang:delete-supported "false";
        type ciena-6500-types:aid;
        description
          "The supporting Termination Point.";
        config true;
      }
      leaf ts-profile {
        yang:create-supported "true";
        yang:get-supported "true";
        yang:edit-supported "true";
        yang:delete-supported "false";
        type ciena-6500-enums:otuTSProfile;
        description
          "TS Profile";
        config true;
      }
      leaf osrp-line-mode {
        yang:create-supported "true";
        yang:get-supported "true";
        yang:edit-supported "false";
        yang:delete-supported "false";
        type enumeration {
          enum ENTIREPORT {
            description
              "This means an OSRP line is at the OTUCn rate.The value disables the OSRP embedded lines feature";
          }
          enum NXODU4 {
            description
              "This value enables the OSRP embedded lines feature ";
          }
        }
        default "ENTIREPORT";
        description
          "This parameter controls the embedded lines behaviour. User can enable/disable the embedded lines using this parameter(Param is applicable only on T-Series shelf.)";
        config true;
      }
      leaf pst {
        yang:create-supported "true";
        yang:get-supported "true";
        yang:edit-supported "false";
        yang:delete-supported "false";
        type enumeration {
          enum IS {
            description
              "In Service(This value can be used in create operation)";
          }
          enum OOS-MA {
            description
              "Out-of-service maintenance for provisioning memory administration(This value can be used in create operation)";
          }
          enum IS-ANR {
            description
              "In Service - Abnormal";
          }
          enum OOS-AU {
            description
              "Out-of-service autonomous from a failure detected point of view. It is not out of service from a state point of view. Alarm is raised if the entity is not able to perform its provisioned functions";
          }
          enum OOS-AUMA {
            description
              "Out-of-service autonomous management - the entity is not able to perform its provisioned functions and is purposefully removed from service";
          }
          enum OOS-MAANR {
            description
              "Out-of-service maintenance - abnormal.";
          }
        }
        description
          "Identify the primary state";
        config true;
      }
      leaf-list sst {
        yang:create-supported "true";
        yang:get-supported "true";
        yang:edit-supported "true";
        yang:delete-supported "false";
        type enumeration {
          enum AINS {
            description
              "Auto-In-Service(This value can be used in create and edit operations)";
          }
          enum AINS-DEA {
            description
              "Auto-In-Service Deactivate(This value can be used in create and edit operations)";
          }
          enum BRIDGED {
            description
              "Transition from switched to bridged";
          }
          enum SWITCHED {
            description
              "Transition from bridged to switched";
          }
          enum ROLL;
          enum ACT;
          enum IDLE;
          enum STBYS;
          enum WRK;
          enum ERRANL;
          enum PSI;
          enum FLT;
          enum MEA;
          enum TSTF;
          enum UEQ;
          enum SGEO;
          enum DISCD;
          enum LPBK;
          enum TS;
          enum FAF;
          enum STBYH;
          enum WRKRX;
          enum WRKTX;
          enum PRTCL;
          enum UAS;
          enum NOSITE;
          enum NOAM;
          enum MON;
          enum MSC;
          enum PROTECTED;
          enum MT {
            description
              "Maintenance(This value can be used in create operation)";
          }
          enum DSBLD;
          enum INHIP;
          enum L2DSBLD;
          enum TSGEN;
          enum TSMON;
          enum TSRECIRC;
          enum TSTIP;
          enum TSTCOMPLD;
          enum TS-DEA;
        }
        description
          "Identify the secondary state";
        config true;
      }
      leaf osrp-tcm-level {
        yang:create-supported "false";
        yang:get-supported "true";
        yang:edit-supported "true";
        yang:delete-supported "false";
        type ciena-6500-types:INT {
          range "1..6";
        }
        description
          "This attribute specifies the TCM level for the OSRP created ODUs under this OTUTTP. The default value is from the attribute OSRPLNTTCMLVL of ED-OSRP-NODE.";
        config true;
      }
      leaf otu-sf-th-lev {
        default "6";
        yang:create-supported "false";
        yang:get-supported "true";
        yang:edit-supported "true";
        yang:delete-supported "false";
        type ciena-6500-types:INT {
          range "6..9";
        }
        description
          "OTU Signal Fail Threshold Level";
        config true;
      }
      leaf encryption-tcm {
        default "1";
        yang:create-supported "false";
        yang:get-supported "true";
        yang:edit-supported "true";
        yang:delete-supported "false";
        type ciena-6500-types:INT {
          range "1..6";
        }
        description
          "This attribute specifies the TCM level for encryption.";
        config true;
      }
      leaf encr-odu1 {
        yang:create-supported "false";
        yang:get-supported "true";
        yang:edit-supported "true";
        yang:delete-supported "false";
        type ciena-6500-enums:EncrByte;
        description
          "Encryption Byte1";
        config true;
      }
      leaf secure-oh {
        yang:create-supported "false";
        yang:get-supported "true";
        yang:edit-supported "true";
        yang:delete-supported "false";
        type ciena-6500-enums:SecureOH;
        description
          "Secure Overhead Bytes";
        config true;
      }
      leaf osrp-channel {
        yang:create-supported "false";
        yang:get-supported "true";
        yang:edit-supported "true";
        yang:delete-supported "false";
        type enumeration {
          enum GCC1 {
            description
              "(This value can be used in edit operation)";
          }
          enum GCC2 {
            description
              "(This value can be used in edit operation)";
          }
          enum NONE {
            description
              "(This value can be used in edit operation)";
          }
          enum GCC0;
        }
        description
          "The OSRP channel(Param is applicable only on T-Series shelf.)";
        config true;
      }
      leaf rx-sapi {
        yang:create-supported "false";
        yang:get-supported "true";
        yang:edit-supported "false";
        yang:delete-supported "false";
        type string {
          length "0..15";
        }
        description
          "The Source Access Point Identifier (SAPI) recovered from the Trail Trace Identifier (TTI) overhead position at the sink of a trail.";
        config false;
      }
      leaf rx-dapi {
        yang:create-supported "false";
        yang:get-supported "true";
        yang:edit-supported "false";
        yang:delete-supported "false";
        type string {
          length "0..15";
        }
        description
          "The Destination Access Point Identifier (DAPI) recovered from the Trail Trace Identifier (TTI) overhead position at the sink of a trail.";
        config false;
      }
      leaf rx-oper {
        yang:create-supported "false";
        yang:get-supported "true";
        yang:edit-supported "false";
        yang:delete-supported "false";
        type string {
          length "0..32";
        }
        description
          "The operator specific part of the Trail Trace Identifier (TTI) information, recovered from the TTI overhead position at the sink of a trail.";
        config false;
      }
      leaf pre-fec-sf-th-ber {
        yang:create-supported "false";
        yang:get-supported "true";
        yang:edit-supported "false";
        yang:delete-supported "false";
        type ciena-6500-types:STRING;
        description
          "Pre-FEC Signal Fail Threshold Bit Error Rate. Parameter applies when FEC is ON";
        config false;
      }
      leaf pre-fec-sd-th-ber {
        yang:create-supported "false";
        yang:get-supported "true";
        yang:edit-supported "false";
        yang:delete-supported "false";
        type ciena-6500-types:STRING;
        description
          "Pre-FEC Signal Degrade Threshold Bit Error Rate. Parameter applies when FEC is ON";
        config false;
      }
      leaf local-sup-cacline-id {
        yang:create-supported "false";
        yang:get-supported "true";
        yang:edit-supported "false";
        yang:delete-supported "false";
        type ciena-6500-types:STRING;
        description
          "The generic cacline end point representing this facility shown in 54xx nomenclature (<bay>-<A|C>-<slot>-<port>)";
        config false;
      }
      leaf timing-reference {
        yang:create-supported "false";
        yang:get-supported "true";
        yang:edit-supported "false";
        yang:delete-supported "false";
        type enumeration {
          enum N {
            description
              "Not a timing reference";
          }
          enum Y {
            description
              "Is a timing reference";
          }
        }
        description
          "Indicates whether the facility is being used as a timing reference";
        config false;
      }
      leaf ains-time-left {
        yang:create-supported "false";
        yang:get-supported "true";
        yang:edit-supported "false";
        yang:delete-supported "false";
        type ciena-6500-types:TIME;
        description
          "The format will be HH-MM for the time left in AINS timeout.";
        config false;
      }
      leaf otu-act-rate {
        yang:create-supported "false";
        yang:get-supported "true";
        yang:edit-supported "false";
        yang:delete-supported "false";
        type ciena-6500-enums:OtuActRate;
        description
          "Actual OTUCn rate, OTUCn(n=1..8)";
        config false;
      }
      leaf act-num-ts {
        default "20";
        yang:create-supported "false";
        yang:get-supported "true";
        yang:edit-supported "false";
        yang:delete-supported "false";
        type ciena-6500-types:INT {
          range "20..320";
        }
        description
          "";
        config false;
      }
      leaf rx-mon {
        yang:create-supported "false";
        yang:get-supported "true";
        yang:edit-supported "false";
        yang:delete-supported "false";
        type ciena-6500-enums:BOOL_YES_NO_defaultYES;
        description
          "Indicate if the signal is monitored in the Rx direction for alarms and PMs and OMs.";
        config false;
      }
      leaf rx-term {
        yang:create-supported "false";
        yang:get-supported "true";
        yang:edit-supported "false";
        yang:delete-supported "false";
        type ciena-6500-enums:BOOL_YES_NO_defaultYES;
        description
          "Indicate if the signal is terminated in the Rx direction or not.";
        config false;
      }
      leaf tx-mon {
        yang:create-supported "false";
        yang:get-supported "true";
        yang:edit-supported "false";
        yang:delete-supported "false";
        type ciena-6500-enums:BOOL_YES_NO_defaultNO;
        description
          "Indicate if the signal is monitored in the Tx direction for alarms and PMs and OMs.";
        config false;
      }
      leaf tx-term {
        yang:create-supported "false";
        yang:get-supported "true";
        yang:edit-supported "false";
        yang:delete-supported "false";
        type ciena-6500-enums:BOOL_YES_NO_defaultNO;
        description
          "Indicate if the signal is terminated in the Tx direction for alarms and PMs and OMs.";
        config false;
      }
      leaf force {
        yang:create-supported "false";
        yang:get-supported "false";
        yang:edit-supported "true";
        yang:delete-supported "false";
        type enumeration {
          enum NO {
            description
              "Do Not Force Edit";
          }
          enum YES {
            description
              "Force Traffic Impacting Edit";
          }
        }
        default "NO";
        description
          "Indicating whether to force an edit when facility still in service (traffic impacting)";
        config true;
      }
    }
    list fttp {
      yang:handler "tl1";
      yang:create-supported "false";
      yang:get-supported "true";
      yang:edit-supported "false";
      yang:delete-supported "false";
      key "fttp";
      config false;
      leaf fttp {
        mandatory true;
        description
          "AID in format FTTP-shelf-slot-port, FTTP-shelf-slot-ALL, FTTP-shelf-ALL, ALL";
        type ciena-6500-types:aid;
      }
      leaf supported-term-pt {
        yang:get-supported "true";
        type ciena-6500-types:aid;
        description
          "The supporting Termination Point.";
        config false;
      }
      leaf local-sup-cacline-id {
        yang:get-supported "true";
        type ciena-6500-types:STRING;
        description
          "The generic cacline end point representing this facility shown in 54xx nomenclature (<bay>-<A|C>-<slot>-<port>)";
        config false;
      }
    }
    list sttp {
      yang:handler "tl1";
      yang:create-supported "true";
      yang:get-supported "true";
      yang:edit-supported "true";
      yang:delete-supported "true";
      key "sttp";
      config true;
      leaf sttp {
        mandatory true;
        description
          "AID in format STTP-shelf-slot-port, STTP-shelf-slot-portSsubport, STTP-shelf-slotSsubslot-port, STTP-shelf-slotSsubslot-portSsubport, STTP-shelf-slot-ALL, STTP-shelf-ALL, ALL";
        type ciena-6500-types:aid;
      }
      leaf rate {
        yang:create-supported "true";
        yang:get-supported "true";
        yang:edit-supported "false";
        yang:delete-supported "false";
        type ciena-6500-enums:SttpRate;
        mandatory true;
        description
          "";
        config true;
      }
      leaf label {
        yang:create-supported "true";
        yang:get-supported "true";
        yang:edit-supported "true";
        yang:delete-supported "false";
        type string {
          length "0..64";
        }
        description
          "User specified Label";
        config true;
      }
      leaf eber-thresh {
        default "3";
        yang:create-supported "true";
        yang:get-supported "true";
        yang:edit-supported "true";
        yang:delete-supported "false";
        type ciena-6500-types:INT {
          range "3 | 4 | 5";
        }
        description
          "Excessive bit error rate threshold value";
        config true;
      }
      leaf sd-th {
        default "6";
        yang:create-supported "true";
        yang:get-supported "true";
        yang:edit-supported "true";
        yang:delete-supported "false";
        type ciena-6500-types:INT {
          range "5..9";
        }
        description
          "Signal Degrade Threshold value";
        config true;
      }
      leaf stformat {
        yang:create-supported "true";
        yang:get-supported "true";
        yang:edit-supported "true";
        yang:delete-supported "false";
        type ciena-6500-enums:stformat;
        default "NUM";
        description
          "Section Trace Format";
        config true;
      }
      leaf stfmode {
        yang:create-supported "true";
        yang:get-supported "true";
        yang:edit-supported "true";
        yang:delete-supported "false";
        type ciena-6500-enums:stfmode;
        default "ALMONLY";
        description
          "Section Trace Fail Mode";
        config true;
      }
      leaf hold-off {
        default "0";
        yang:create-supported "true";
        yang:get-supported "true";
        yang:edit-supported "true";
        yang:delete-supported "false";
        type ciena-6500-types:INT {
          range "0 | 10 | 20..1000";
        }
        description
          "Conditioning holdoff timer.";
        config true;
      }
      leaf mapping {
        yang:create-supported "true";
        yang:get-supported "true";
        yang:edit-supported "true";
        yang:delete-supported "false";
        type ciena-6500-enums:SttpMapping;
        description
          "Defines the mapping of this facility and the children that it will have.";
        config true;
      }
      leaf pst {
        yang:create-supported "true";
        yang:get-supported "true";
        yang:edit-supported "false";
        yang:delete-supported "false";
        type enumeration {
          enum IS {
            description
              "In Service(This value can be used in create operation)";
          }
          enum OOS-MA {
            description
              "Out-of-service maintenance for provisioning memory administration(This value can be used in create operation)";
          }
          enum IS-ANR {
            description
              "In Service - Abnormal";
          }
          enum OOS-AU {
            description
              "Out-of-service autonomous from a failure detected point of view. It is not out of service from a state point of view. Alarm is raised if the entity is not able to perform its provisioned functions";
          }
          enum OOS-AUMA {
            description
              "Out-of-service autonomous management - the entity is not able to perform its provisioned functions and is purposefully removed from service";
          }
          enum OOS-MAANR {
            description
              "Out-of-service maintenance - abnormal.";
          }
        }
        description
          "Identify the primary state";
        config true;
      }
      leaf-list sst {
        yang:create-supported "true";
        yang:get-supported "true";
        yang:edit-supported "true";
        yang:delete-supported "false";
        type enumeration {
          enum AINS {
            description
              "Auto-In-Service(This value can be used in create operation)";
          }
          enum AINS-DEA {
            description
              "Auto-In-Service Deactivate(This value can be used in create operation)";
          }
          enum BRIDGED {
            description
              "Transition from switched to bridged";
          }
          enum SWITCHED {
            description
              "Transition from bridged to switched";
          }
          enum ROLL;
          enum ACT;
          enum IDLE;
          enum STBYS;
          enum WRK;
          enum ERRANL;
          enum PSI;
          enum FLT;
          enum MEA;
          enum TSTF;
          enum UEQ;
          enum SGEO;
          enum DISCD;
          enum LPBK;
          enum TS {
            description
              "Test Access(This value can be used in create and edit operations)";
          }
          enum FAF;
          enum STBYH;
          enum WRKRX;
          enum WRKTX;
          enum PRTCL;
          enum UAS;
          enum NOSITE;
          enum NOAM;
          enum MON;
          enum MSC;
          enum PROTECTED;
          enum MT {
            description
              "Maintenance(This value can be used in create operation)";
          }
          enum DSBLD;
          enum INHIP;
          enum L2DSBLD;
          enum TSGEN;
          enum TSMON;
          enum TSRECIRC;
          enum TSTIP;
          enum TSTCOMPLD;
          enum TS-DEA {
            description
              "Test Access Deactivate(This value can be used in create and edit operations)";
          }
        }
        description
          "Identify the secondary state";
        config true;
      }
      leaf exp-trc {
        yang:create-supported "false";
        yang:get-supported "true";
        yang:edit-supported "true";
        yang:delete-supported "false";
        type string {
          length "0..16";
        }
        description
          "";
        config true;
      }
      leaf tx-trc {
        yang:create-supported "false";
        yang:get-supported "true";
        yang:edit-supported "true";
        yang:delete-supported "false";
        type ciena-6500-types:STRING;
        description
          "The transmitted Section Trace value";
        config true;
      }
      leaf supported-term-pt {
        yang:create-supported "false";
        yang:get-supported "true";
        yang:edit-supported "false";
        yang:delete-supported "false";
        type ciena-6500-types:aid;
        description
          "The supporting Termination Point.";
        config false;
      }
      leaf port-mode {
        yang:create-supported "false";
        yang:get-supported "true";
        yang:edit-supported "false";
        yang:delete-supported "false";
        type ciena-6500-enums:STTPportmode;
        description
          "Optical Port Market Preference";
        config false;
      }
      leaf local-sup-cacline-id {
        yang:create-supported "false";
        yang:get-supported "true";
        yang:edit-supported "false";
        yang:delete-supported "false";
        type ciena-6500-types:STRING;
        description
          "The generic cacline end point representing this facility shown in 54xx nomenclature (<bay>-<A|C>-<slot>-<port>)";
        config false;
      }
      leaf rx-trc {
        default "UNKNOWN";
        yang:create-supported "false";
        yang:get-supported "true";
        yang:edit-supported "false";
        yang:delete-supported "false";
        type ciena-6500-types:STRING;
        description
          "The Received Section Trace value";
        config false;
      }
      leaf uneqmode {
        yang:create-supported "false";
        yang:get-supported "true";
        yang:edit-supported "false";
        yang:delete-supported "false";
        type ciena-6500-enums:uneqmode;
        description
          "Unequipped Insertion Mode";
        config false;
      }
      leaf rxmon {
        yang:create-supported "false";
        yang:get-supported "true";
        yang:edit-supported "false";
        yang:delete-supported "false";
        type ciena-6500-enums:BOOL_YES_NO_defaultYES;
        description
          "Indicate if the signal is monitored in the Rx direction for alarms and PMs and OMs.";
        config false;
      }
      leaf rxterm {
        yang:create-supported "false";
        yang:get-supported "true";
        yang:edit-supported "false";
        yang:delete-supported "false";
        type ciena-6500-enums:BOOL_YES_NO_defaultYES;
        description
          "Indicate if the signal is terminated in the Rx direction or not.";
        config false;
      }
      leaf tx-mon {
        yang:create-supported "false";
        yang:get-supported "true";
        yang:edit-supported "false";
        yang:delete-supported "false";
        type ciena-6500-enums:BOOL_YES_NO_defaultNO;
        description
          "Indicate if the signal is monitored in the Tx direction for alarms and PMs and OMs.";
        config false;
      }
      leaf tx-term {
        yang:create-supported "false";
        yang:get-supported "true";
        yang:edit-supported "false";
        yang:delete-supported "false";
        type ciena-6500-enums:BOOL_YES_NO_defaultNO;
        description
          "Indicate if the signal is terminated in the Tx direction for alarms and PMs and OMs.";
        config false;
      }
      leaf timing-reference {
        yang:create-supported "false";
        yang:get-supported "true";
        yang:edit-supported "false";
        yang:delete-supported "false";
        type enumeration {
          enum N {
            description
              "Not a timing reference";
          }
          enum Y {
            description
              "Is a timing reference";
          }
        }
        description
          "Indicates whether the facility is being used as a timing reference";
        config false;
      }
      leaf expstrc {
        yang:create-supported "true";
        yang:get-supported "false";
        yang:edit-supported "false";
        yang:delete-supported "false";
        type ciena-6500-types:STRING;
        description
          "";
        config true;
      }
      leaf txstrc {
        yang:create-supported "true";
        yang:get-supported "false";
        yang:edit-supported "false";
        yang:delete-supported "false";
        type ciena-6500-types:STRING;
        description
          "The transmitted Section Trace value";
        config true;
      }
    }
    list ettp {
      yang:handler "tl1";
      yang:create-supported "true";
      yang:get-supported "true";
      yang:edit-supported "true";
      yang:delete-supported "true";
      key "ettp";
      config true;
      leaf ettp {
        mandatory true;
        description
          "AID in format ETTP-shelf-slot-port, ETTP-shelf-slot-portSsubport, ETTP-shelf-slot-port-rt1Ptp1, ETTP-shelf-slot-portSsubport-rt1Ptp1, ETTP-shelf-slotSsubslot-portSsubport, ETTP-shelf-slotSsubslot-port, ETTP-shelf-slot-port-rt1Ptp1-rt2Ptp2, ETTP-shelf-slot-port-rt1Ptp1-rt2Ptp2-rt3Ptp3, ETTP-shelf-slot-port-rt1Ptp1-rt2Ptp2-rt3Ptp3-rt4Ptp4, ETTP-shelf-slot-portSsubport-rt1Ptp1-rt2Ptp2, ETTP-shelf-slotSsubslot-portSsubport-rt1Ptp1, ETTP-shelf-slotSsubslot-portSsubport-rt1Ptp1-rt2Ptp2, ETTP-shelf-slotSsubslot-port-rt1Ptp1, ETTP-shelf-slotSsubslot-port-rt1Ptp1-rt2Ptp2, ETTP-shelf-slotSsubslot-port-rt1Ptp1-rt2Ptp2-rt3Ptp3, ETTP-shelf-slot-ALL, ETTP-shelf-ALL, ETTP-shelf-slot-port-ALL, ALL";
        type ciena-6500-types:aid;
      }
      leaf label {
        yang:create-supported "true";
        yang:get-supported "true";
        yang:edit-supported "true";
        yang:delete-supported "false";
        type string {
          length "0..64";
        }
        description
          "User specified Label";
        config true;
      }
      leaf mapping {
        yang:create-supported "true";
        yang:get-supported "true";
        yang:edit-supported "true";
        yang:delete-supported "false";
        type ciena-6500-enums:EttpMapping;
        description
          "Defines the mapping of this facility and the children that it will have.";
        config true;
      }
      leaf hold-off {
        default "100";
        yang:create-supported "true";
        yang:get-supported "true";
        yang:edit-supported "true";
        yang:delete-supported "false";
        type ciena-6500-types:INT {
          range "0 | 10 | 20..1000";
        }
        description
          "Conditioning holdoff time in seconds.";
        config true;
      }
      leaf max-transmit-unit {
        yang:create-supported "true";
        yang:get-supported "true";
        yang:edit-supported "true";
        yang:delete-supported "false";
        type enumeration {
          enum 1600 {
            description
              "(This value can be used in create and edit operations)";
          }
          enum 9600 {
            description
              "(This value can be used in create and edit operations)";
          }
          enum 2000 {
            description
              "(This value can be used in edit operation)";
          }
        }
        description
          "Maximum Transmission Unit (actually MRU)";
        config true;
      }
      leaf fec-frmt {
        yang:create-supported "true";
        yang:get-supported "true";
        yang:edit-supported "true";
        yang:delete-supported "false";
        type enumeration {
          enum OFF {
            description
              "NO FEC";
          }
          enum RS10 {
            description
              "RS10 FEC";
          }
          enum RS10_KP4 {
            description
              "RS10_KP4 FEC";
          }
        }
        description
          "FEC Format";
        config true;
      }
      leaf pre-fec-sf-th-lev {
        yang:create-supported "true";
        yang:get-supported "true";
        yang:edit-supported "true";
        yang:delete-supported "false";
        type ciena-6500-types:STRING;
        description
          "Pre-FEC Signal Fail Threshold Level.";
        config true;
      }
      leaf pre-fec-sd-th-lev {
        yang:create-supported "true";
        yang:get-supported "true";
        yang:edit-supported "true";
        yang:delete-supported "false";
        type ciena-6500-types:STRING;
        description
          "Pre-FEC Signal Degrade Threshold Level.";
        config true;
      }
      leaf cond-type {
        yang:create-supported "true";
        yang:get-supported "true";
        yang:edit-supported "true";
        yang:delete-supported "false";
        type ciena-6500-enums:EttpCondType;
        description
          "Specifies ethernet specific client conditioning behaviour.";
        config true;
      }
      leaf rate {
        yang:create-supported "true";
        yang:get-supported "true";
        yang:edit-supported "false";
        yang:delete-supported "false";
        type ciena-6500-enums:EthRate;
        description
          "";
        config true;
      }
      leaf lldpmon {
        yang:create-supported "true";
        yang:get-supported "true";
        yang:edit-supported "true";
        yang:delete-supported "false";
        type ciena-6500-enums:BOOL_ON_OFF;
        description
          "Specifies if facility is monitoring LLDP packets or not.";
        config true;
      }
      leaf time-slot-assignment {
        yang:create-supported "true";
        yang:get-supported "true";
        yang:edit-supported "true";
        yang:delete-supported "false";
        type string {
          length "1..9";
        }
        description
          "Time slots assigned to ETTP.";
        config true;
      }
      leaf pst {
        yang:create-supported "true";
        yang:get-supported "true";
        yang:edit-supported "false";
        yang:delete-supported "false";
        type enumeration {
          enum IS {
            description
              "In Service(This value can be used in create operation)";
          }
          enum OOS-MA {
            description
              "Out-of-service maintenance for provisioning memory administration(This value can be used in create operation)";
          }
          enum IS-ANR {
            description
              "In Service - Abnormal";
          }
          enum OOS-AU {
            description
              "Out-of-service autonomous from a failure detected point of view. It is not out of service from a state point of view. Alarm is raised if the entity is not able to perform its provisioned functions";
          }
          enum OOS-AUMA {
            description
              "Out-of-service autonomous management - the entity is not able to perform its provisioned functions and is purposefully removed from service";
          }
          enum OOS-MAANR {
            description
              "Out-of-service maintenance - abnormal.";
          }
        }
        description
          "Identify the primary state";
        config true;
      }
      leaf-list sst {
        yang:create-supported "true";
        yang:get-supported "true";
        yang:edit-supported "true";
        yang:delete-supported "false";
        type enumeration {
          enum AINS {
            description
              "Auto-In-Service(This value can be used in create and edit operations)";
          }
          enum AINS-DEA {
            description
              "Auto-In-Service Deactivate(This value can be used in create and edit operations)";
          }
          enum BRIDGED {
            description
              "Transition from switched to bridged";
          }
          enum SWITCHED {
            description
              "Transition from bridged to switched";
          }
          enum ROLL;
          enum ACT;
          enum IDLE;
          enum STBYS;
          enum WRK;
          enum ERRANL;
          enum PSI;
          enum FLT;
          enum MEA;
          enum TSTF;
          enum UEQ;
          enum SGEO;
          enum DISCD;
          enum LPBK;
          enum TS;
          enum FAF;
          enum STBYH;
          enum WRKRX;
          enum WRKTX;
          enum PRTCL;
          enum UAS;
          enum NOSITE;
          enum NOAM;
          enum MON;
          enum MSC;
          enum PROTECTED;
          enum MT {
            description
              "Maintenance(This value can be used in create and edit operations)";
          }
          enum DSBLD;
          enum INHIP;
          enum L2DSBLD;
          enum TSGEN;
          enum TSMON;
          enum TSRECIRC;
          enum TSTIP;
          enum TSTCOMPLD;
          enum TS-DEA;
        }
        description
          "Identify the secondary state";
        config true;
      }
      leaf flow-ctrl {
        yang:create-supported "false";
        yang:get-supported "true";
        yang:edit-supported "true";
        yang:delete-supported "false";
        type enumeration {
          enum NONE;
          enum ASYM;
          enum PREE;
          enum SYM;
        }
        default "NONE";
        description
          "Flow control mechanism.";
        config true;
      }
      leaf if-type {
        yang:create-supported "false";
        yang:get-supported "true";
        yang:edit-supported "true";
        yang:delete-supported "false";
        type enumeration {
          enum UNI;
          enum E-NNI;
          enum I-NNI;
        }
        description
          "Interface Type";
        config true;
      }
      leaf pre-fec-sf-th-ber {
        yang:create-supported "false";
        yang:get-supported "true";
        yang:edit-supported "true";
        yang:delete-supported "false";
        type ciena-6500-types:STRING;
        description
          "Pre-FEC Signal Fail Threshold Bit Error Rate.";
        config true;
      }
      leaf pre-fec-sd-th-ber {
        yang:create-supported "false";
        yang:get-supported "true";
        yang:edit-supported "true";
        yang:delete-supported "false";
        type ciena-6500-types:STRING;
        description
          "Pre-FEC Signal Degrade Threshold Bit Error Rate.";
        config true;
      }
      leaf supported-term-pt {
        yang:create-supported "false";
        yang:get-supported "true";
        yang:edit-supported "false";
        yang:delete-supported "false";
        type ciena-6500-types:aid;
        description
          "The supporting Termination Point.";
        config false;
      }
      leaf mode {
        yang:create-supported "false";
        yang:get-supported "true";
        yang:edit-supported "false";
        yang:delete-supported "false";
        type enumeration {
          enum TERMINATED;
          enum MONITORED;
        }
        description
          "MAC or PHY layer terminated or monitored";
        config false;
      }
      leaf local-sup-cacline-id {
        yang:create-supported "false";
        yang:get-supported "true";
        yang:edit-supported "false";
        yang:delete-supported "false";
        type ciena-6500-types:STRING;
        description
          "The generic cacline end point representing this facility shown in 54xx nomenclature (<bay>-<A|C>-<slot>-<port>)";
        config false;
      }
      leaf l2-in-use-act {
        yang:create-supported "false";
        yang:get-supported "true";
        yang:edit-supported "false";
        yang:delete-supported "false";
        type enumeration {
          enum NO {
            description
              "The facility is not used by Layer 2 active configuration ";
          }
          enum YES {
            description
              "The facility is used by Layer 2 active configuration";
          }
        }
        description
          "In use in Layer 2 Active Configuration";
        config false;
      }
      leaf l2-in-use-sav {
        yang:create-supported "false";
        yang:get-supported "true";
        yang:edit-supported "false";
        yang:delete-supported "false";
        type enumeration {
          enum NO {
            description
              "The facility is not used by Layer 2 saved configuration ";
          }
          enum YES {
            description
              "The facility is used by Layer 2 saved configuration ";
          }
        }
        description
          "In use in Layer 2 Saved Configuration";
        config false;
      }
      leaf timing-reference {
        yang:create-supported "false";
        yang:get-supported "true";
        yang:edit-supported "false";
        yang:delete-supported "false";
        type enumeration {
          enum N {
            description
              "Not a timing reference";
          }
          enum Y {
            description
              "Is a timing reference";
          }
        }
        description
          "Indicates whether the facility is being used as a timing reference";
        config false;
      }
      leaf service-rate {
        yang:create-supported "false";
        yang:get-supported "true";
        yang:edit-supported "false";
        yang:delete-supported "false";
        type ciena-6500-types:INT {
          range "0 | 50 | 100..100000";
        }
        description
          "Service rate of the Ethernet Flex in Mbps.";
        config false;
      }
      leaf transport-rate {
        yang:create-supported "false";
        yang:get-supported "true";
        yang:edit-supported "false";
        yang:delete-supported "false";
        type ciena-6500-types:INT {
          range "0..104117";
        }
        description
          "Transport rate of the Ethernet Flex in Mbps. The ODUFlex rate.";
        config false;
      }
      leaf reserved {
        yang:create-supported "false";
        yang:get-supported "true";
        yang:edit-supported "false";
        yang:delete-supported "false";
        type ciena-6500-enums:BOOL_YES_NO;
        description
          "Specify if the facility is being reserved for packet SNC's";
        config false;
      }
      leaf rsrvd-oper {
        yang:create-supported "false";
        yang:get-supported "true";
        yang:edit-supported "false";
        yang:delete-supported "false";
        type ciena-6500-enums:BOOL_YES_NO;
        description
          "Indicates if the reservation is operational for reserved ETTP's";
        config false;
      }
      leaf rx-mon {
        yang:create-supported "false";
        yang:get-supported "true";
        yang:edit-supported "false";
        yang:delete-supported "false";
        type ciena-6500-enums:BOOL_YES_NO_defaultYES;
        description
          "Indicate if the signal is monitored in the Rx direction for alarms and PMs and OMs.";
        config false;
      }
      leaf rx-term {
        yang:create-supported "false";
        yang:get-supported "true";
        yang:edit-supported "false";
        yang:delete-supported "false";
        type ciena-6500-enums:BOOL_YES_NO_defaultYES;
        description
          "Indicate if the signal is terminated in the Rx direction or not.";
        config false;
      }
      leaf tx-mon {
        yang:create-supported "false";
        yang:get-supported "true";
        yang:edit-supported "false";
        yang:delete-supported "false";
        type ciena-6500-enums:BOOL_YES_NO_defaultNO;
        description
          "Indicate if the signal is monitored in the Tx direction for alarms and PMs and OMs.";
        config false;
      }
      leaf tx-term {
        yang:create-supported "false";
        yang:get-supported "true";
        yang:edit-supported "false";
        yang:delete-supported "false";
        type ciena-6500-enums:BOOL_YES_NO_defaultNO;
        description
          "Indicate if the signal is terminated in the Tx direction for alarms and PMs and OMs.";
        config false;
      }
      leaf ains-time-left {
        yang:create-supported "false";
        yang:get-supported "true";
        yang:edit-supported "false";
        yang:delete-supported "false";
        type ciena-6500-types:TIME;
        description
          "The format will be HH-MM for the time left in AINS timeout.";
        config false;
      }
      leaf force {
        yang:create-supported "false";
        yang:get-supported "false";
        yang:edit-supported "true";
        yang:delete-supported "false";
        type enumeration {
          enum NO {
            description
              "Do Not Force Edit";
          }
          enum YES {
            description
              "Force Traffic Impacting Edit";
          }
        }
        default "NO";
        description
          "Indicating whether to force an edit when facility still in service (traffic impacting)";
        config true;
      }
    }
    list oduttp {
      yang:handler "tl1";
      yang:create-supported "true";
      yang:get-supported "true";
      yang:edit-supported "true";
      yang:delete-supported "true";
      key "oduttp";
      config true;
      leaf oduttp {
        mandatory true;
        description
          "AID in format ODUTTP-shelf-slot-port-rt1Ptp1, ODUTTP-shelf-slot-port-rt1Ptp1-rt2Ptp2, ODUTTP-shelf-slot-port-rt1Ptp1-rt2Ptp2-rt3Ptp3, ODUTTP-shelf-slot-port-rt1Ptp1-rt2Ptp2-rt3Ptp3-rt4Ptp4, ODUTTP-shelf-slot-portSsubport-rt1Ptp1, ODUTTP-shelf-slot-portSsubport-rt1Ptp1-rt2Ptp2, ODUTTP-shelf-slotSsubslot-portSsubport-rt1Ptp1, ODUTTP-shelf-slotSsubslot-portSsubport-rt1Ptp1-rt2Ptp2, ODUTTP-shelf-slotSsubslot-port-rt1Ptp1, ODUTTP-shelf-slotSsubslot-port-rt1Ptp1-rt2Ptp2, ODUTTP-shelf-slotSsubslot-port-rt1Ptp1-rt2Ptp2-rt3Ptp3, ODUTTP-shelf-slot-portPsubport-rt1Ptp1, ODUTTP-shelf-slot-portPsubport-rt1Ptp1-rt2Ptp2, ODUTTP-shelf-slot-port-rt1Ptp1-ALL, ODUTTP-shelf-slot-port-ALL, ODUTTP-shelf-slot-ALL, ODUTTP-shelf-slot-portPsubport-ALL, ODUTTP-shelf-slot-port-rt1Ptp1-rt2Ptp2-rt3Ptp3-ALL, ODUTTP-shelf-slot-port-rt1Ptp1-rt2Ptp2-ALL, ODUTTP-shelf-ALL, ODUTTP-shelf-slot-portSsubport-ALL, ALL";
        type ciena-6500-types:aid;
      }
      leaf rate {
        yang:create-supported "true";
        yang:get-supported "true";
        yang:edit-supported "false";
        yang:delete-supported "false";
        type ciena-6500-enums:OduTtpRate;
        description
          "Rate";
        config true;
      }
      leaf trib-slot-assignment {
        yang:create-supported "true";
        yang:get-supported "true";
        yang:edit-supported "true";
        yang:delete-supported "false";
        type string {
          length "1..99";
        }
        description
          "The tributary slots used by this ODU.";
        config true;
      }
      leaf label {
        yang:create-supported "true";
        yang:get-supported "true";
        yang:edit-supported "true";
        yang:delete-supported "false";
        type string {
          length "0..64";
        }
        description
          "User specified Label";
        config true;
      }
      leaf tx-sapi {
        yang:create-supported "true";
        yang:get-supported "true";
        yang:edit-supported "true";
        yang:delete-supported "false";
        type string {
          length "0..15";
        }
        description
          "The Source Access Point Identifier (SAPI), provisioned by the managing system at the termination source, to be placed in the Trail Trace Identifier (TTI) overhead position of the source of a trail.";
        config true;
      }
      leaf tx-dapi {
        yang:create-supported "true";
        yang:get-supported "true";
        yang:edit-supported "true";
        yang:delete-supported "false";
        type string {
          length "0..15";
        }
        description
          "The Destination Access Point Identifier (DAPI), provisioned by the managing system at the termination source, to be placed in the Trail Trace Identifier (TTI) overhead position of the source of a trail.";
        config true;
      }
      leaf tx-oper {
        yang:create-supported "true";
        yang:get-supported "true";
        yang:edit-supported "true";
        yang:delete-supported "false";
        type string {
          length "0..32";
        }
        description
          "The operator specific part of the Trail Trace Identifier (TTI) information, provisioned by the managing system at the termination source, to be placed in the TTI overhead position of the source of a trail.";
        config true;
      }
      leaf ex-sapi {
        yang:create-supported "true";
        yang:get-supported "true";
        yang:edit-supported "true";
        yang:delete-supported "false";
        type string {
          length "0..15";
        }
        description
          "The expected Source Access Point Identifier (SAPI), provisioned by the managing system, to be compared with the received SAPI at the overhead position of the sink for the purpose of checking the integrity of connectivity. ";
        config true;
      }
      leaf ex-dapi {
        yang:create-supported "true";
        yang:get-supported "true";
        yang:edit-supported "true";
        yang:delete-supported "false";
        type string {
          length "0..15";
        }
        description
          "The expected Destination Access Point Identifier (DAPI), provisioned by the managing system, to be compared with the received DAPI at the overhead position of the sink for the purpose of checking the integrity of connectivity. ";
        config true;
      }
      leaf ex-oper {
        yang:create-supported "true";
        yang:get-supported "true";
        yang:edit-supported "true";
        yang:delete-supported "false";
        type string {
          length "0..32";
        }
        description
          "The expected operator specific part of the Trail Trace Identifier (TTI) information, provisioned by the managing system at the termination source, to be placed in the TTI overhead position of the source of a trail.";
        config true;
      }
      leaf ex-pt {
        yang:create-supported "true";
        yang:get-supported "true";
        yang:edit-supported "true";
        yang:delete-supported "false";
        type string {
          length "2";
        }
        description
          "The expected payload type.";
        config true;
      }
      leaf ts-size {
        yang:create-supported "true";
        yang:get-supported "true";
        yang:edit-supported "false";
        yang:delete-supported "false";
        type enumeration {
          enum ODU0 {
            description
              "ODU0 is the tributary slot size (unit)";
          }
          enum ODU1 {
            description
              "ODU1 is the tributary slot size (unit)";
          }
        }
        description
          "The tributary slot size";
        config true;
      }
      leaf tf-mode {
        yang:create-supported "true";
        yang:get-supported "true";
        yang:edit-supported "true";
        yang:delete-supported "false";
        type ciena-6500-enums:otntfMode;
        default "OFF";
        description
          "Trace Fail Mode";
        config true;
      }
      leaf tim-enable {
        yang:create-supported "true";
        yang:get-supported "true";
        yang:edit-supported "true";
        yang:delete-supported "false";
        type enumeration {
          enum TIM_SAPI_ONLY {
            description
              "Only checks for SAPI mismatch";
          }
          enum TIM_DAPI_ONLY {
            description
              "Only checks for DAPI mismatch";
          }
          enum TIM_SAPI_DAPI {
            description
              "Checks for SAPI and DAPI mismatch";
          }
          enum TIM_OPER_SPEC {
            description
              "Checks for Operator Specific mismatch";
          }
        }
        description
          "The Trail Trace Identifier Mismatch (TIM) controls checking for Trace Identifier Mismatch fault detection. ";
        config true;
      }
      leaf-list cond-type {
        yang:create-supported "true";
        yang:get-supported "true";
        yang:edit-supported "true";
        yang:delete-supported "false";
        type ciena-6500-enums:OduCtpCondType;
        description
          "Conditioning behaviour on client faults. ";
        config true;
      }
      leaf dm-enable {
        yang:create-supported "true";
        yang:get-supported "true";
        yang:edit-supported "true";
        yang:delete-supported "false";
        type enumeration {
          enum YES;
          enum NO;
        }
        default "YES";
        description
          "Specify if delay measurement is enable.";
        config true;
      }
      leaf odu1-interop {
        yang:create-supported "true";
        yang:get-supported "true";
        yang:edit-supported "true";
        yang:delete-supported "false";
        type enumeration {
          enum OTHER {
            description
              "Interop with equipment other than 2G5 MOTR";
          }
          enum 2G5MOTR {
            description
              "Interop with equipment 2G5 MOTR";
          }
        }
        description
          "Required Interop Equipment Type";
        config true;
      }
      leaf rx-ts-mode {
        yang:create-supported "true";
        yang:get-supported "true";
        yang:edit-supported "true";
        yang:delete-supported "false";
        type ciena-6500-enums:rxtsMode;
        default "OFF";
        description
          "Received Tributary Slot Mode";
        config true;
      }
      leaf client-type {
        yang:create-supported "true";
        yang:get-supported "true";
        yang:edit-supported "false";
        yang:delete-supported "false";
        type ciena-6500-enums:clientTypeTtp;
        description
          "Server layer client type";
        config true;
      }
      leaf base-ho {
        yang:create-supported "true";
        yang:get-supported "true";
        yang:edit-supported "true";
        yang:delete-supported "false";
        type ciena-6500-enums:baseHO;
        description
          "Base HO ODUk";
        config true;
      }
      leaf bit-rate {
        yang:create-supported "true";
        yang:get-supported "true";
        yang:edit-supported "true";
        yang:delete-supported "false";
        type string {
          length "0..19";
        }
        description
          "Define the bit rate of flex.";
        config true;
      }
      leaf tolerance {
        yang:create-supported "true";
        yang:get-supported "true";
        yang:edit-supported "false";
        yang:delete-supported "false";
        type string {
          length "0..64";
        }
        description
          "Define the tolerance in ppm of oduflex payload.";
        config true;
      }
      leaf sd-th {
        default "9";
        yang:create-supported "true";
        yang:get-supported "true";
        yang:edit-supported "true";
        yang:delete-supported "false";
        type ciena-6500-types:INT {
          range "6..9";
        }
        description
          "Signal Degrade Threshold Value";
        config true;
      }
      leaf sf-th {
        default "0";
        yang:create-supported "true";
        yang:get-supported "true";
        yang:edit-supported "true";
        yang:delete-supported "false";
        type ciena-6500-types:INT {
          range "0..9";
        }
        description
          "Signal Fail Threshold Level.";
        config true;
      }
      leaf trib-slot-prov {
        yang:create-supported "true";
        yang:get-supported "true";
        yang:edit-supported "true";
        yang:delete-supported "false";
        type ciena-6500-enums:TsProv;
        description
          "tribSlot provision";
        config true;
      }
      leaf degm-intv {
        default "2";
        yang:create-supported "true";
        yang:get-supported "true";
        yang:edit-supported "true";
        yang:delete-supported "false";
        type ciena-6500-types:INT {
          range "2..10";
        }
        description
          "Consecutive bad intervals required to declare signal degrade";
        config true;
      }
      leaf degthr-percentage {
        default "100";
        yang:create-supported "true";
        yang:get-supported "true";
        yang:edit-supported "true";
        yang:delete-supported "false";
        type ciena-6500-types:INT {
          range "1..1000";
        }
        description
          "Percentage of errored blocks required to declare an interval bad";
        config true;
      }
      leaf flex-type {
        yang:create-supported "true";
        yang:get-supported "true";
        yang:edit-supported "false";
        yang:delete-supported "false";
        type ciena-6500-enums:flexType;
        description
          "ODU flex type(Param is applicable only on T-Series shelf.)";
        config true;
      }
      leaf gcc1-mode {
        yang:create-supported "true";
        yang:get-supported "true";
        yang:edit-supported "true";
        yang:delete-supported "false";
        type ciena-6500-enums:GCCMode;
        description
          "GCC1 Aggregation mode";
        config true;
      }
      leaf gcc2-mode {
        yang:create-supported "true";
        yang:get-supported "true";
        yang:edit-supported "true";
        yang:delete-supported "false";
        type ciena-6500-enums:GCCMode;
        description
          "GCC2 Aggregation mode";
        config true;
      }
      leaf pst {
        yang:create-supported "true";
        yang:get-supported "true";
        yang:edit-supported "false";
        yang:delete-supported "false";
        type enumeration {
          enum IS {
            description
              "In Service(This value can be used in create operation)";
          }
          enum OOS-MA {
            description
              "Out-of-service maintenance for provisioning memory administration(This value can be used in create operation)";
          }
          enum IS-ANR {
            description
              "In Service - Abnormal";
          }
          enum OOS-AU {
            description
              "Out-of-service autonomous from a failure detected point of view. It is not out of service from a state point of view. Alarm is raised if the entity is not able to perform its provisioned functions";
          }
          enum OOS-AUMA {
            description
              "Out-of-service autonomous management - the entity is not able to perform its provisioned functions and is purposefully removed from service";
          }
          enum OOS-MAANR {
            description
              "Out-of-service maintenance - abnormal.";
          }
        }
        description
          "Identify the primary state";
        config true;
      }
      leaf num-ts {
        yang:create-supported "false";
        yang:get-supported "true";
        yang:edit-supported "true";
        yang:delete-supported "false";
        type ciena-6500-types:INT {
          range "1..320";
        }
        description
          "Used to identify the number of tributaries comprising this TTP.";
        config true;
      }
      leaf rx-sapi {
        yang:create-supported "false";
        yang:get-supported "true";
        yang:edit-supported "false";
        yang:delete-supported "false";
        type string {
          length "0..15";
        }
        description
          "The Source Access Point Identifier (SAPI) recovered from the Trail Trace Identifier (TTI) overhead position at the sink of a trail.";
        config false;
      }
      leaf rx-dapi {
        yang:create-supported "false";
        yang:get-supported "true";
        yang:edit-supported "false";
        yang:delete-supported "false";
        type string {
          length "0..15";
        }
        description
          "The Destination Access Point Identifier (DAPI) recovered from the Trail Trace Identifier (TTI) overhead position at the sink of a trail.";
        config false;
      }
      leaf rx-oper {
        yang:create-supported "false";
        yang:get-supported "true";
        yang:edit-supported "false";
        yang:delete-supported "false";
        type string {
          length "0..32";
        }
        description
          "The operator specific part of the Trail Trace Identifier (TTI) information, recovered from the TTI overhead position at the sink of a trail.";
        config false;
      }
      leaf rx-pt {
        yang:create-supported "false";
        yang:get-supported "true";
        yang:edit-supported "false";
        yang:delete-supported "false";
        type string {
          length "2";
        }
        description
          "The received payload type.";
        config false;
      }
      leaf dm-count {
        yang:create-supported "false";
        yang:get-supported "true";
        yang:edit-supported "false";
        yang:delete-supported "false";
        type ciena-6500-types:STRING;
        description
          "Value of delay measurement of ODU in micro seconds.";
        config false;
      }
      leaf line-prot-group {
        yang:create-supported "false";
        yang:get-supported "true";
        yang:edit-supported "false";
        yang:delete-supported "false";
        type ciena-6500-types:aid;
        description
          "Line Protection Group in AID format";
        config false;
      }
      leaf line-prot-role {
        yang:create-supported "false";
        yang:get-supported "true";
        yang:edit-supported "false";
        yang:delete-supported "false";
        type enumeration {
          enum UNPROTECTED;
          enum WORK;
          enum PROTECT;
          enum WORK_PROTECT;
        }
        description
          "Line Protection Role";
        config false;
      }
      leaf line-prot-type {
        yang:create-supported "false";
        yang:get-supported "true";
        yang:edit-supported "false";
        yang:delete-supported "false";
        type enumeration {
          enum NOT_PROTECTED;
          enum APS_PROTECTED;
        }
        description
          "Line Protection Type";
        config false;
      }
      leaf owner {
        yang:create-supported "false";
        yang:get-supported "true";
        yang:edit-supported "false";
        yang:delete-supported "false";
        type ciena-6500-enums:Owner;
        description
          "Specifies who created this TTP.";
        config false;
      }
      leaf supported-term-pt {
        yang:create-supported "false";
        yang:get-supported "true";
        yang:edit-supported "false";
        yang:delete-supported "false";
        type ciena-6500-types:aid;
        description
          "The supporting Termination Point.";
        config false;
      }
      leaf rx-ts {
        yang:create-supported "false";
        yang:get-supported "true";
        yang:edit-supported "false";
        yang:delete-supported "false";
        type string {
          length "1..99";
        }
        description
          "Received tributary slots.";
        config false;
      }
      leaf ex-rx-ts {
        yang:create-supported "false";
        yang:get-supported "true";
        yang:edit-supported "false";
        yang:delete-supported "false";
        type string {
          length "1..99";
        }
        description
          "Expected Receive tributary slots.";
        config false;
      }
      leaf resizeable {
        yang:create-supported "false";
        yang:get-supported "true";
        yang:edit-supported "false";
        yang:delete-supported "false";
        type ciena-6500-enums:BOOL_YES_NO;
        description
          "ODUFlex is resizeable";
        config false;
      }
      leaf local-sup-cacline-id {
        yang:create-supported "false";
        yang:get-supported "true";
        yang:edit-supported "false";
        yang:delete-supported "false";
        type ciena-6500-types:STRING;
        description
          "The generic cacline end point representing this facility shown in 54xx nomenclature (<bay>-<A|C>-<slot>-<port>)";
        config false;
      }
      leaf anchor-ts {
        yang:create-supported "false";
        yang:get-supported "true";
        yang:edit-supported "false";
        yang:delete-supported "false";
        type ciena-6500-types:INT {
          range "1..80";
        }
        description
          "Anchor of tx triburtary slot";
        config false;
      }
      leaf prov-msi {
        yang:create-supported "false";
        yang:get-supported "true";
        yang:edit-supported "false";
        yang:delete-supported "false";
        type string {
          length "1..1600";
        }
        description
          "Provisioned MSI for all tributary slots.";
        config false;
      }
      leaf rx-msi {
        yang:create-supported "false";
        yang:get-supported "true";
        yang:edit-supported "false";
        yang:delete-supported "false";
        type string {
          length "1..1600";
        }
        description
          "Actual received MSI for all tributary slots.";
        config false;
      }
      leaf timing-reference {
        yang:create-supported "false";
        yang:get-supported "true";
        yang:edit-supported "false";
        yang:delete-supported "false";
        type enumeration {
          enum N {
            description
              "Not a timing reference";
          }
          enum Y {
            description
              "Is a timing reference";
          }
        }
        description
          "Indicates whether the facility is being used as a timing reference";
        config false;
      }
      leaf reserved {
        yang:create-supported "false";
        yang:get-supported "true";
        yang:edit-supported "false";
        yang:delete-supported "false";
        type ciena-6500-enums:BOOL_YES_NO;
        description
          "Specify if the facility is being reserved for packet SNC's";
        config false;
      }
      leaf act-avail-ts {
        yang:create-supported "false";
        yang:get-supported "true";
        yang:edit-supported "false";
        yang:delete-supported "false";
        type string {
          length "1..320";
        }
        description
          "Actual available TS supported by the TRANSMODE.";
        config false;
      }
      leaf rxmon {
        yang:create-supported "false";
        yang:get-supported "true";
        yang:edit-supported "false";
        yang:delete-supported "false";
        type ciena-6500-enums:BOOL_YES_NO_defaultNO;
        description
          "Indicate if the signal is monitored in the Rx direction for alarms and PMs and OMs.";
        config false;
      }
      leaf rxterm {
        yang:create-supported "false";
        yang:get-supported "true";
        yang:edit-supported "false";
        yang:delete-supported "false";
        type ciena-6500-enums:BOOL_YES_NO_defaultNO;
        description
          "Indicate if the signal is terminated in the Rx direction or not.";
        config false;
      }
      leaf tx-mon {
        yang:create-supported "false";
        yang:get-supported "true";
        yang:edit-supported "false";
        yang:delete-supported "false";
        type ciena-6500-enums:BOOL_YES_NO_defaultNO;
        description
          "Indicate if the signal is monitored in the Tx direction for alarms and PMs and OMs.";
        config false;
      }
      leaf tx-term {
        yang:create-supported "false";
        yang:get-supported "true";
        yang:edit-supported "false";
        yang:delete-supported "false";
        type ciena-6500-enums:BOOL_YES_NO_defaultNO;
        description
          "Indicate if the signal is terminated in the Tx direction for alarms and PMs and OMs.";
        config false;
      }
      leaf-list sst {
        yang:create-supported "false";
        yang:get-supported "true";
        yang:edit-supported "false";
        yang:delete-supported "false";
        type ciena-6500-enums:SSTfac;
        description
          "Secondary State";
        config false;
      }
      leaf force {
        yang:create-supported "true";
        yang:get-supported "false";
        yang:edit-supported "true";
        yang:delete-supported "false";
        type enumeration {
          enum NO {
            description
              "Do not override/preempt";
          }
          enum YES {
            description
              "Override/preempt reserved ODUTTP with the same tribport";
          }
        }
        default "NO";
        description
          "Indicating whether to override/preempt a reserved ODUTTP";
        config true;
      }
    }
    list msi-oduttp {
      yang:handler "tl1";
      yang:create-supported "false";
      yang:get-supported "true";
      yang:edit-supported "false";
      yang:delete-supported "false";
      key "oduttp";
      config false;
      leaf oduttp {
        mandatory true;
        description
          "AID in format ODUTTP-shelf-slot-port-rt1Ptp1, ODUTTP-shelf-slot-port-rt1Ptp1-rt2Ptp2, ODUTTP-shelf-slot-port-rt1Ptp1-rt2Ptp2-rt3Ptp3, ODUTTP-shelf-slot-port-rt1Ptp1-rt2Ptp2-rt3Ptp3-rt4Ptp4, ODUTTP-shelf-slot-portSsubport-rt1Ptp1, ODUTTP-shelf-slot-portSsubport-rt1Ptp1-rt2Ptp2, ODUTTP-shelf-slot-portPsubport-rt1Ptp1-rt2Ptp2, ODUTTP-shelf-slot-portPsubport-rt1Ptp1, ODUTTP-shelf-slot-port-rt1Ptp1-ALL, ODUTTP-shelf-slot-port-ALL, ODUTTP-shelf-slot-ALL, ODUTTP-shelf-slot-portPsubport-ALL, ODUTTP-shelf-slot-port-rt1Ptp1-rt2Ptp2-rt3Ptp3-ALL, ODUTTP-shelf-slot-port-rt1Ptp1-rt2Ptp2-ALL, ODUTTP-shelf-ALL, ODUTTP-shelf-slot-portSsubport-ALL, ODUTTP-shelf-slotSsubslot-port-rt1Ptp1, ODUTTP-shelf-slotSsubslot-portSsubport-rt1Ptp1, ODUTTP-shelf-slotSsubslot-portSsubport-rt1Ptp1-rt2Ptp2, ODUTTP-shelf-slotSsubslot-port-rt1Ptp1-rt2Ptp2, ODUTTP-shelf-slotSsubslot-port-rt1Ptp1-rt2Ptp2-rt3Ptp3, ALL";
        type ciena-6500-types:aid;
      }
      leaf prov-msi1 {
        yang:get-supported "true";
        type string {
          length "1..200";
        }
        description
          "Provisioned MSI for OPUC #1.";
        config false;
      }
      leaf prov-msi2 {
        yang:get-supported "true";
        type string {
          length "1..100";
        }
        description
          "Provisioned MSI for OPUC #2.";
        config false;
      }
      leaf prov-msi3 {
        yang:get-supported "true";
        type string {
          length "1..100";
        }
        description
          "Provisioned MSI for OPUC #3.";
        config false;
      }
      leaf prov-msi4 {
        yang:get-supported "true";
        type string {
          length "1..100";
        }
        description
          "Provisioned MSI for OPUC #4.";
        config false;
      }
      leaf prov-msi5 {
        yang:get-supported "true";
        type string {
          length "1..100";
        }
        description
          "Provisioned MSI for OPUC #5.";
        config false;
      }
      leaf prov-msi6 {
        yang:get-supported "true";
        type string {
          length "1..100";
        }
        description
          "Provisioned MSI for OPUC #6.";
        config false;
      }
      leaf prov-msi7 {
        yang:get-supported "true";
        type string {
          length "1..100";
        }
        description
          "Provisioned MSI for OPUC #7.";
        config false;
      }
      leaf prov-msi8 {
        yang:get-supported "true";
        type string {
          length "1..100";
        }
        description
          "Provisioned MSI for OPUC #8.";
        config false;
      }
      leaf prov-msi9 {
        yang:get-supported "true";
        type string {
          length "1..100";
        }
        description
          "Provisioned MSI for OPUC #9.";
        config false;
      }
      leaf prov-msi10 {
        yang:get-supported "true";
        type string {
          length "1..100";
        }
        description
          "Provisioned MSI for OPUC #10.";
        config false;
      }
      leaf prov-msi11 {
        yang:get-supported "true";
        type string {
          length "1..100";
        }
        description
          "Provisioned MSI for OPUC #11.";
        config false;
      }
      leaf prov-msi12 {
        yang:get-supported "true";
        type string {
          length "1..100";
        }
        description
          "Provisioned MSI for OPUC #12.";
        config false;
      }
      leaf prov-msi13 {
        yang:get-supported "true";
        type string {
          length "1..100";
        }
        description
          "Provisioned MSI for OPUC #13.";
        config false;
      }
      leaf prov-msi14 {
        yang:get-supported "true";
        type string {
          length "1..100";
        }
        description
          "Provisioned MSI for OPUC #14.";
        config false;
      }
      leaf prov-msi15 {
        yang:get-supported "true";
        type string {
          length "1..100";
        }
        description
          "Provisioned MSI for OPUC #15.";
        config false;
      }
      leaf prov-msi16 {
        yang:get-supported "true";
        type string {
          length "1..100";
        }
        description
          "Provisioned MSI for OPUC #16.";
        config false;
      }
      leaf rx-msi1 {
        yang:get-supported "true";
        type string {
          length "1..200";
        }
        description
          "Actual received MSI for OPUC #1.";
        config false;
      }
      leaf rx-msi2 {
        yang:get-supported "true";
        type string {
          length "1..100";
        }
        description
          "Actual received MSI for OPUC #2.";
        config false;
      }
      leaf rx-msi3 {
        yang:get-supported "true";
        type string {
          length "1..100";
        }
        description
          "Actual received MSI for OPUC #3.";
        config false;
      }
      leaf rx-msi4 {
        yang:get-supported "true";
        type string {
          length "1..100";
        }
        description
          "Actual received MSI for OPUC #4.";
        config false;
      }
      leaf rx-msi5 {
        yang:get-supported "true";
        type string {
          length "1..100";
        }
        description
          "Actual received MSI for OPUC #5.";
        config false;
      }
      leaf rx-msi6 {
        yang:get-supported "true";
        type string {
          length "1..100";
        }
        description
          "Actual received MSI for OPUC #6.";
        config false;
      }
      leaf rx-msi7 {
        yang:get-supported "true";
        type string {
          length "1..100";
        }
        description
          "Actual received MSI for OPUC #7.";
        config false;
      }
      leaf rx-msi8 {
        yang:get-supported "true";
        type string {
          length "1..100";
        }
        description
          "Actual received MSI for OPUC #8.";
        config false;
      }
      leaf rx-msi9 {
        yang:get-supported "true";
        type string {
          length "1..100";
        }
        description
          "Actual received MSI for OPUC #9.";
        config false;
      }
      leaf rx-msi10 {
        yang:get-supported "true";
        type string {
          length "1..100";
        }
        description
          "Actual received MSI for OPUC #10.";
        config false;
      }
      leaf rx-msi11 {
        yang:get-supported "true";
        type string {
          length "1..100";
        }
        description
          "Actual received MSI for OPUC #11.";
        config false;
      }
      leaf rx-msi12 {
        yang:get-supported "true";
        type string {
          length "1..100";
        }
        description
          "Actual received MSI for OPUC #12.";
        config false;
      }
      leaf rx-msi13 {
        yang:get-supported "true";
        type string {
          length "1..100";
        }
        description
          "Actual received MSI for OPUC #13.";
        config false;
      }
      leaf rx-msi14 {
        yang:get-supported "true";
        type string {
          length "1..100";
        }
        description
          "Actual received MSI for OPUC #14.";
        config false;
      }
      leaf rx-msi15 {
        yang:get-supported "true";
        type string {
          length "1..100";
        }
        description
          "Actual received MSI for OPUC #15.";
        config false;
      }
      leaf rx-msi16 {
        yang:get-supported "true";
        type string {
          length "1..100";
        }
        description
          "Actual received MSI for OPUC #16.";
        config false;
      }
    }
    list oductp {
      yang:handler "tl1";
      yang:create-supported "true";
      yang:get-supported "true";
      yang:edit-supported "true";
      yang:delete-supported "true";
      key "oductp";
      config true;
      leaf oductp {
        mandatory true;
        description
          "AID in format ODUCTP-shelf-slot-port-rt1Ptp1, ODUCTP-shelf-slot-port-rt1Ptp1-rt2Ptp2, ODUCTP-shelf-slot-port-rt1Ptp1-rt2Ptp2-rt3Ptp3, ODUCTP-shelf-slot-port-rt1Ptp1-rt2Ptp2-rt3Ptp3-rt4Ptp4, ODUCTP-shelf-slot-portSsubport-rt1Ptp1, ODUCTP-shelf-slot-portSsubport-rt1Ptp1-rt2Ptp2, ODUCTP-shelf-slotSsubslot-portSsubport-rt1Ptp1, ODUCTP-shelf-slotSsubslot-portSsubport-rt1Ptp1-rt2Ptp2, ODUCTP-shelf-slotSsubslot-port-rt1Ptp1, ODUCTP-shelf-slotSsubslot-port-rt1Ptp1-rt2Ptp2, ODUCTP-shelf-slotSsubslot-port-rt1Ptp1-rt2Ptp2-rt3Ptp3, ODUCTP-shelf-slot-portPsubport-rt1Ptp1, ODUCTP-shelf-slotSsubslot-port-rt1Ptp1-rt2Ptp2-rt3Ptp3-rt4Ptp4, ODUCTP-shelf-slot-portPsubport-rt1Ptp1-rt2Ptp2, ODUCTP-shelf-slot-portPsubport-rt1Ptp1-rt2Ptp2-rt3Ptp3, ODUCTP-shelf-slot-port-rt1Ptp1-rt2Ptp2-rt3Ptp3-rt4Ptp4-ALL, ODUCTP-shelf-slot-port-rt1Ptp1-rt2Ptp2-rt3Ptp3-ALL, ODUCTP-shelf-slot-port-rt1Ptp1-rt2Ptp2-ALL, ODUCTP-shelf-slot-port-rt1Ptp1-ALL, ODUCTP-shelf-slot-port-ALL, ODUCTP-shelf-slot-ALL, ODUCTP-shelf-ALL, ODUCTP-shelf-slot-portPsubport-ALL, ODUCTP-shelf-slot-portSsubport-ALL, ODUCTP-shelf-slot-portPsubport-rt1Ptp1-ALL, ALL";
        type ciena-6500-types:aid;
      }
      leaf rate {
        yang:create-supported "true";
        yang:get-supported "true";
        yang:edit-supported "false";
        yang:delete-supported "false";
        type ciena-6500-enums:OduCtpRate;
        description
          "Rate";
        config true;
      }
      leaf ctp-mode {
        yang:create-supported "true";
        yang:get-supported "true";
        yang:edit-supported "true";
        yang:delete-supported "false";
        type enumeration {
          enum TRANSPARENT;
          enum MONITOR;
          enum TERMINATED;
        }
        description
          "The mode of the ODUCTP.";
        config true;
      }
      leaf trib-slot-assignment {
        yang:create-supported "true";
        yang:get-supported "true";
        yang:edit-supported "true";
        yang:delete-supported "false";
        type string {
          length "1..99";
        }
        description
          "The tributary slots used by this ODU.";
        config true;
      }
      leaf label {
        yang:create-supported "true";
        yang:get-supported "true";
        yang:edit-supported "true";
        yang:delete-supported "false";
        type string {
          length "0..64";
        }
        description
          "User specified Label";
        config true;
      }
      leaf tim-enable {
        yang:create-supported "true";
        yang:get-supported "true";
        yang:edit-supported "true";
        yang:delete-supported "false";
        type enumeration {
          enum TIM_SAPI_ONLY {
            description
              "Only checks for SAPI mismatch";
          }
          enum TIM_DAPI_ONLY {
            description
              "Only checks for DAPI mismatch";
          }
          enum TIM_SAPI_DAPI {
            description
              "Checks for SAPI and DAPI mismatch";
          }
          enum TIM_OPER_SPEC {
            description
              "Checks for Operator Specific mismatch";
          }
        }
        default "TIM_OPER_SPEC";
        description
          "The Trail Trace Identifier Mismatch (TIM) controls checking for Trace Identifier Mismatch fault detection. ";
        config true;
      }
      leaf tf-mode {
        yang:create-supported "true";
        yang:get-supported "true";
        yang:edit-supported "true";
        yang:delete-supported "false";
        type ciena-6500-enums:otntfMode;
        default "OFF";
        description
          "Trace Fail Mode";
        config true;
      }
      leaf rx-ts-mode {
        yang:create-supported "true";
        yang:get-supported "true";
        yang:edit-supported "true";
        yang:delete-supported "false";
        type ciena-6500-enums:rxtsMode;
        default "OFF";
        description
          "Received Tributary Slot Mode";
        config true;
      }
      leaf client-type {
        yang:create-supported "true";
        yang:get-supported "true";
        yang:edit-supported "true";
        yang:delete-supported "false";
        type ciena-6500-enums:clientTypeCtp;
        description
          "Indicate the type of client signal";
        config true;
      }
      leaf bit-rate {
        yang:create-supported "true";
        yang:get-supported "true";
        yang:edit-supported "true";
        yang:delete-supported "false";
        type string {
          length "0..19";
        }
        description
          "Define the bit rate of flex.";
        config true;
      }
      leaf tolerance {
        yang:create-supported "true";
        yang:get-supported "true";
        yang:edit-supported "false";
        yang:delete-supported "false";
        type string {
          length "0..64";
        }
        description
          "Define the tolerance in ppm of oduflex payload.";
        config true;
      }
      leaf flex-type {
        yang:create-supported "true";
        yang:get-supported "true";
        yang:edit-supported "true";
        yang:delete-supported "false";
        type ciena-6500-enums:flexType;
        description
          "ODU flex type";
        config true;
      }
      leaf gep {
        yang:create-supported "true";
        yang:get-supported "true";
        yang:edit-supported "true";
        yang:delete-supported "false";
        type enumeration {
          enum YES;
          enum NO;
        }
        default "NO";
        description
          "Specifies whether the end-point facility accepts Generict End Point (GEP) method.";
        config true;
      }
      leaf gep-name {
        yang:create-supported "true";
        yang:get-supported "true";
        yang:edit-supported "true";
        yang:delete-supported "false";
        type string {
          length "1..64";
        }
        description
          "Specifies the Generict End Point (GEP) name.";
        config true;
      }
      leaf trib-slot-prov {
        yang:create-supported "true";
        yang:get-supported "true";
        yang:edit-supported "true";
        yang:delete-supported "false";
        type ciena-6500-enums:TsProv;
        description
          "tribSlot provision";
        config true;
      }
      leaf sd-th {
        default "9";
        yang:create-supported "true";
        yang:get-supported "true";
        yang:edit-supported "true";
        yang:delete-supported "false";
        type ciena-6500-types:INT {
          range "6..9";
        }
        description
          "Signal degrade threshold value";
        config true;
      }
      leaf sf-th {
        default "0";
        yang:create-supported "true";
        yang:get-supported "true";
        yang:edit-supported "true";
        yang:delete-supported "false";
        type ciena-6500-types:INT {
          range "0..9";
        }
        description
          "Signal Fail Threshold Level.";
        config true;
      }
      leaf tx-sapi {
        yang:create-supported "true";
        yang:get-supported "true";
        yang:edit-supported "true";
        yang:delete-supported "false";
        type string {
          length "0..15";
        }
        description
          "The Source Access Point Identifier (SAPI), provisioned by the managing system at the termination source, to be placed in the Trail Trace Identifier (TTI) overhead position of the source of a trail.";
        config true;
      }
      leaf tx-dapi {
        yang:create-supported "true";
        yang:get-supported "true";
        yang:edit-supported "true";
        yang:delete-supported "false";
        type string {
          length "0..15";
        }
        description
          "The Destination Access Point Identifier (DAPI), provisioned by the managing system at the termination source, to be placed in the Trail Trace Identifier (TTI) overhead position of the source of a trail.";
        config true;
      }
      leaf tx-oper {
        yang:create-supported "true";
        yang:get-supported "true";
        yang:edit-supported "true";
        yang:delete-supported "false";
        type string {
          length "0..32";
        }
        description
          "The operator specific part of the Trail Trace Identifier (TTI) information, provisioned by the managing system at the termination source, to be placed in the TTI overhead position of the source of a trail.";
        config true;
      }
      leaf ex-sapi {
        yang:create-supported "true";
        yang:get-supported "true";
        yang:edit-supported "true";
        yang:delete-supported "false";
        type string {
          length "0..15";
        }
        description
          "The expected Source Access Point Identifier (SAPI), provisioned by the managing system, to be compared with the received SAPI at the overhead position of the sink for the purpose of checking the integrity of connectivity. ";
        config true;
      }
      leaf ex-dapi {
        yang:create-supported "true";
        yang:get-supported "true";
        yang:edit-supported "true";
        yang:delete-supported "false";
        type string {
          length "0..15";
        }
        description
          "The expected Destination Access Point Identifier (DAPI), provisioned by the managing system, to be compared with the received DAPI at the overhead position of the sink for the purpose of checking the integrity of connectivity. ";
        config true;
      }
      leaf ex-oper {
        yang:create-supported "true";
        yang:get-supported "true";
        yang:edit-supported "true";
        yang:delete-supported "false";
        type string {
          length "0..32";
        }
        description
          "The expected operator specific part of the Trail Trace Identifier (TTI) information, provisioned by the managing system at the termination source, to be placed in the TTI overhead position of the source of a trail.";
        config true;
      }
      leaf-list cond-type {
        yang:create-supported "true";
        yang:get-supported "true";
        yang:edit-supported "true";
        yang:delete-supported "false";
        type ciena-6500-enums:OduCtpCondType;
        description
          "Conditioning behaviour on client faults. ";
        config true;
      }
      leaf degm-intv {
        default "2";
        yang:create-supported "true";
        yang:get-supported "true";
        yang:edit-supported "true";
        yang:delete-supported "false";
        type ciena-6500-types:INT {
          range "2..10";
        }
        description
          "Consecutive bad intervals required to declare signal degrade";
        config true;
      }
      leaf degthr-percentage {
        default "100";
        yang:create-supported "true";
        yang:get-supported "true";
        yang:edit-supported "true";
        yang:delete-supported "false";
        type ciena-6500-types:INT {
          range "1..1000";
        }
        description
          "Percentage of errored blocks required to declare an interval bad";
        config true;
      }
      leaf-list oductp-rxcondtrig {
        yang:create-supported "true";
        yang:get-supported "true";
        yang:edit-supported "true";
        yang:delete-supported "false";
        type ciena-6500-enums:rxCondTrig;
        description
          "Determines if Plug Fail/Card Fail and xTTP Port OOS trigger on-ramp conditioning";
        config true;
      }
      leaf dm-enable {
        yang:create-supported "true";
        yang:get-supported "true";
        yang:edit-supported "true";
        yang:delete-supported "false";
        type ciena-6500-enums:BOOL_YES_NO;
        description
          "Specify if delay measurement is enable.";
        config true;
      }
      leaf num-ts {
        yang:create-supported "true";
        yang:get-supported "true";
        yang:edit-supported "true";
        yang:delete-supported "false";
        type ciena-6500-types:INT {
          range "1..320";
        }
        description
          "Used to identify the number of tributaries comprising this CTP.";
        config true;
      }
      leaf num-flexts {
        yang:create-supported "true";
        yang:get-supported "true";
        yang:edit-supported "true";
        yang:delete-supported "false";
        type ciena-6500-types:INT {
          range "1..320";
        }
        description
          "Used to identify the number of flex tributaries comprising this CTP.(Param is applicable only on T-Series shelf.)";
        config true;
      }
      leaf pst {
        yang:create-supported "true";
        yang:get-supported "true";
        yang:edit-supported "false";
        yang:delete-supported "false";
        type enumeration {
          enum IS {
            description
              "In Service(This value can be used in create operation)";
          }
          enum OOS-MA {
            description
              "Out-of-service maintenance for provisioning memory administration(This value can be used in create operation)";
          }
          enum IS-ANR {
            description
              "In Service - Abnormal";
          }
          enum OOS-AU {
            description
              "Out-of-service autonomous from a failure detected point of view. It is not out of service from a state point of view. Alarm is raised if the entity is not able to perform its provisioned functions";
          }
          enum OOS-AUMA {
            description
              "Out-of-service autonomous management - the entity is not able to perform its provisioned functions and is purposefully removed from service";
          }
          enum OOS-MAANR {
            description
              "Out-of-service maintenance - abnormal.";
          }
        }
        description
          "Identify the primary state";
        config true;
      }
      leaf ex-pt {
        yang:create-supported "false";
        yang:get-supported "true";
        yang:edit-supported "true";
        yang:delete-supported "false";
        type string {
          length "2";
        }
        description
          "The expected payload type.";
        config true;
      }
      leaf rx-sapi {
        yang:create-supported "false";
        yang:get-supported "true";
        yang:edit-supported "false";
        yang:delete-supported "false";
        type string {
          length "0..15";
        }
        description
          "The Source Access Point Identifier (SAPI) recovered from the Trail Trace Identifier (TTI) overhead position at the sink of a trail.";
        config false;
      }
      leaf rx-dapi {
        yang:create-supported "false";
        yang:get-supported "true";
        yang:edit-supported "false";
        yang:delete-supported "false";
        type string {
          length "0..15";
        }
        description
          "The Destination Access Point Identifier (DAPI) recovered from the Trail Trace Identifier (TTI) overhead position at the sink of a trail.";
        config false;
      }
      leaf rx-oper {
        yang:create-supported "false";
        yang:get-supported "true";
        yang:edit-supported "false";
        yang:delete-supported "false";
        type string {
          length "0..32";
        }
        description
          "The operator specific part of the Trail Trace Identifier (TTI) information, recovered from the TTI overhead position at the sink of a trail.";
        config false;
      }
      leaf rx-pt {
        yang:create-supported "false";
        yang:get-supported "true";
        yang:edit-supported "false";
        yang:delete-supported "false";
        type string {
          length "2";
        }
        description
          "The received payload type.";
        config false;
      }
      leaf dm-count {
        yang:create-supported "false";
        yang:get-supported "true";
        yang:edit-supported "false";
        yang:delete-supported "false";
        type ciena-6500-types:STRING;
        description
          "Value of delay measurement of ODU in micro seconds.";
        config false;
      }
      leaf owner {
        yang:create-supported "false";
        yang:get-supported "true";
        yang:edit-supported "false";
        yang:delete-supported "false";
        type ciena-6500-enums:Owner;
        description
          "Specifies who created this CTP.";
        config false;
      }
      leaf supported-term-pt {
        yang:create-supported "false";
        yang:get-supported "true";
        yang:edit-supported "false";
        yang:delete-supported "false";
        type ciena-6500-types:aid;
        description
          "The supporting Termination Point.";
        config false;
      }
      leaf rx-ts {
        yang:create-supported "false";
        yang:get-supported "true";
        yang:edit-supported "false";
        yang:delete-supported "false";
        type string {
          length "1..99";
        }
        description
          "Received tributary slots.";
        config false;
      }
      leaf ex-rx-ts {
        yang:create-supported "false";
        yang:get-supported "true";
        yang:edit-supported "false";
        yang:delete-supported "false";
        type string {
          length "1..99";
        }
        description
          "Expected receive tributary slots.";
        config false;
      }
      leaf resizeable {
        yang:create-supported "false";
        yang:get-supported "true";
        yang:edit-supported "false";
        yang:delete-supported "false";
        type ciena-6500-enums:BOOL_YES_NO;
        description
          "ODUFlex is resizeable";
        config false;
      }
      leaf base-ho {
        yang:create-supported "false";
        yang:get-supported "true";
        yang:edit-supported "false";
        yang:delete-supported "false";
        type ciena-6500-enums:baseHO;
        description
          "Base HO ODUk";
        config false;
      }
      leaf act-avail-ts {
        yang:create-supported "false";
        yang:get-supported "true";
        yang:edit-supported "false";
        yang:delete-supported "false";
        type string {
          length "1..320";
        }
        description
          "Actual available TS supported by the TRANSMODE.";
        config false;
      }
      leaf rx-mon {
        yang:create-supported "false";
        yang:get-supported "true";
        yang:edit-supported "false";
        yang:delete-supported "false";
        type ciena-6500-enums:BOOL_YES_NO_defaultNO;
        description
          "Indicate if the signal is monitored in the Rx direction for alarms and PMs and OMs.";
        config false;
      }
      leaf rx-term {
        yang:create-supported "false";
        yang:get-supported "true";
        yang:edit-supported "false";
        yang:delete-supported "false";
        type ciena-6500-enums:BOOL_YES_NO_defaultNO;
        description
          "Indicate if the signal is terminated in the Rx direction or not.";
        config false;
      }
      leaf tx-mon {
        yang:create-supported "false";
        yang:get-supported "true";
        yang:edit-supported "false";
        yang:delete-supported "false";
        type ciena-6500-enums:BOOL_YES_NO_defaultNO;
        description
          "Indicate if the signal is monitored in the Tx direction for alarms and PMs and OMs.";
        config false;
      }
      leaf tx-term {
        yang:create-supported "false";
        yang:get-supported "true";
        yang:edit-supported "false";
        yang:delete-supported "false";
        type ciena-6500-enums:BOOL_YES_NO_defaultNO;
        description
          "Indicate if the signal is terminated in the Tx direction for alarms and PMs and OMs.";
        config false;
      }
      leaf-list caid {
        yang:create-supported "false";
        yang:get-supported "true";
        yang:edit-supported "false";
        yang:delete-supported "false";
        type ciena-6500-types:aid;
        description
          "Specify the list of M2M PTP AIDs those are required for Mate to Mate Interconnection. Format: M2MPTP1&M2MPTP2&...";
        config false;
      }
      leaf-list sst {
        yang:create-supported "false";
        yang:get-supported "true";
        yang:edit-supported "false";
        yang:delete-supported "false";
        type ciena-6500-enums:SSTfac;
        description
          "Secondary State";
        config false;
      }
      leaf force {
        yang:create-supported "true";
        yang:get-supported "false";
        yang:edit-supported "true";
        yang:delete-supported "false";
        type enumeration {
          enum NO {
            description
              "Do not override/preempt";
          }
          enum YES {
            description
              "Override/preempt reserved ODUTTP with the same tribport";
          }
        }
        default "NO";
        description
          "Indicating whether to override/preempt a reserved ODUTTP";
        config true;
      }
    }
    list tcm {
      yang:handler "tl1";
      yang:create-supported "true";
      yang:get-supported "true";
      yang:edit-supported "true";
      yang:delete-supported "true";
      key "tcm";
      config true;
      leaf tcm {
        mandatory true;
        description
          "AID in format TCMTTP-shelf-slot-port-rt1Ptp1Ttcm, TCMTTP-shelf-slot-port-rt1Ptp1-rt2Ptp2Ttcm, TCMTTP-shelf-slot-port-rt1Ptp1-rt2Ptp2-rt3Ptp3Ttcm, TCMTTP-shelf-slot-port-rt1Ptp1-rt2Ptp2-rt3Ptp3-rt4Ptp4Ttcm, TCMTTP-shelf-slot-portSsubport-rt1Ptp1Ttcm, TCMTTP-shelf-slot-portSsubport-rt1Ptp1-rt2Ptp2Ttcm, TCMTTP-shelf-slotSsubslot-port-rt1Ptp1-rt2Ptp2Ttcm, TCMTTP-shelf-slot-portPsubport-rt1Ptp1Ttcm, TCMTTP-shelf-slotSsubslot-portSsubport-rt1Ptp1Ttcm, TCMTTP-shelf-slotSsubslot-portSsubport-rt1Ptp1-rt2Ptp2Ttcm, TCMTTP-shelf-slotSsubslot-port-rt1Ptp1Ttcm, TCMTTP-shelf-slotSsubslot-port-rt1Ptp1-rt2Ptp2-rt3Ptp3Ttcm, TCMTTP-shelf-slotSsubslot-port-rt1Ptp1-rt2Ptp2-rt3Ptp3-rt4Ptp4Ttcm, TCMCTP-shelf-slot-port-rt1Ptp1Ttcm, TCMCTP-shelf-slot-port-rt1Ptp1-rt2Ptp2Ttcm, TCMCTP-shelf-slot-port-rt1Ptp1-rt2Ptp2-rt3Ptp3Ttcm, TCMCTP-shelf-slot-port-rt1Ptp1-rt2Ptp2-rt3Ptp3-rt4Ptp4Ttcm, TCMCTP-shelf-slot-portSsubport-rt1Ptp1Ttcm, TCMCTP-shelf-slot-portPsubport-rt1Ptp1Ttcm, TCMCTP-shelf-slot-portSsubport-rt1Ptp1-rt2Ptp2Ttcm, TCMCTP-shelf-slotSsubslot-portSsubport-rt1Ptp1Ttcm, TCMCTP-shelf-slotSsubslot-portSsubport-rt1Ptp1-rt2Ptp2Ttcm, TCMCTP-shelf-slotSsubslot-port-rt1Ptp1Ttcm, TCMCTP-shelf-slotSsubslot-port-rt1Ptp1-rt2Ptp2Ttcm, TCMCTP-shelf-slotSsubslot-port-rt1Ptp1-rt2Ptp2-rt3Ptp3Ttcm, TCMCTP-shelf-slotSsubslot-port-rt1Ptp1-rt2Ptp2-rt3Ptp3-rt4Ptp4Ttcm, TCMTTP-shelf-slot-portPsubport-ALL, TCMTTP-shelf-slot-port-ALL, TCMTTP-shelf-slot-port-rt1Ptp1-rt2Ptp2-rt3Ptp3-rt4Ptp4-ALL, TCMTTP-shelf-slot-port-rt1Ptp1-rt2Ptp2-rt3Ptp3-ALL, TCMTTP-shelf-slot-port-rt1Ptp1-rt2Ptp2-ALL, TCMTTP-shelf-slot-port-rt1Ptp1-ALL, TCMTTP-shelf-slot-ALL, TCMTTP-shelf-ALL, TCMTTP-shelf-slot-portSsubport-ALL, TCMCTP-shelf-slot-port-ALL, TCMCTP-shelf-slot-port-rt1Ptp1-rt2Ptp2-rt3Ptp3-rt4Ptp4-ALL, TCMCTP-shelf-slot-port-rt1Ptp1-rt2Ptp2-rt3Ptp3-ALL, TCMCTP-shelf-slot-port-rt1Ptp1-rt2Ptp2-ALL, TCMCTP-shelf-slot-port-rt1Ptp1-ALL, TCMCTP-shelf-slot-ALL, TCMCTP-shelf-ALL, TCMCTP-shelf-slot-portSsubport-ALL, ALL";
        type ciena-6500-types:aid;
      }
      leaf label {
        yang:create-supported "true";
        yang:get-supported "true";
        yang:edit-supported "true";
        yang:delete-supported "false";
        type string {
          length "0..64";
        }
        description
          "User specified Label";
        config true;
      }
      leaf tcm-mode {
        yang:create-supported "true";
        yang:get-supported "true";
        yang:edit-supported "false";
        yang:delete-supported "false";
        type ciena-6500-enums:tcmMode;
        description
          "Identifies the mode of the TCM. ";
        config true;
      }
      leaf sd-th {
        default "9";
        yang:create-supported "true";
        yang:get-supported "true";
        yang:edit-supported "true";
        yang:delete-supported "false";
        type ciena-6500-types:INT {
          range "6..9";
        }
        description
          "Signal degrade threshold value";
        config true;
      }
      leaf tx-sapi {
        yang:create-supported "true";
        yang:get-supported "true";
        yang:edit-supported "true";
        yang:delete-supported "false";
        type string {
          length "0..15";
        }
        description
          "The Source Access Point Identifier (SAPI), provisioned by the managing system at the termination source, to be placed in the Trail Trace Identifier (TTI) overhead position of the source of a trail.";
        config true;
      }
      leaf tx-dapi {
        yang:create-supported "true";
        yang:get-supported "true";
        yang:edit-supported "true";
        yang:delete-supported "false";
        type string {
          length "0..15";
        }
        description
          "The Destination Access Point Identifier (DAPI), provisioned by the managing system at the termination source, to be placed in the Trail Trace Identifier (TTI) overhead position of the source of a trail.";
        config true;
      }
      leaf tx-oper {
        yang:create-supported "true";
        yang:get-supported "true";
        yang:edit-supported "true";
        yang:delete-supported "false";
        type string {
          length "0..32";
        }
        description
          "The operator specific part of the Trail Trace Identifier (TTI) information, provisioned by the managing system at the termination source, to be placed in the TTI overhead position of the source of a trail.";
        config true;
      }
      leaf ex-sapi {
        yang:create-supported "true";
        yang:get-supported "true";
        yang:edit-supported "true";
        yang:delete-supported "false";
        type string {
          length "0..15";
        }
        description
          "The expected Source Access Point Identifier (SAPI), provisioned by the managing system, to be compared with the received SAPI at the overhead position of the sink for the purpose of checking the integrity of connectivity. ";
        config true;
      }
      leaf ex-dapi {
        yang:create-supported "true";
        yang:get-supported "true";
        yang:edit-supported "true";
        yang:delete-supported "false";
        type string {
          length "0..15";
        }
        description
          "The expected Destination Access Point Identifier (DAPI), provisioned by the managing system, to be compared with the received DAPI at the overhead position of the sink for the purpose of checking the integrity of connectivity. ";
        config true;
      }
      leaf ex-oper {
        yang:create-supported "true";
        yang:get-supported "true";
        yang:edit-supported "true";
        yang:delete-supported "false";
        type string {
          length "0..32";
        }
        description
          "The expected operator specific part of the Trail Trace Identifier (TTI) information, provisioned by the managing system at the termination source, to be placed in the TTI overhead position of the source of a trail.";
        config true;
      }
      leaf tim-enable {
        yang:create-supported "true";
        yang:get-supported "true";
        yang:edit-supported "true";
        yang:delete-supported "false";
        type enumeration {
          enum TIM_SAPI_ONLY {
            description
              "Only checks for SAPI mismatch";
          }
          enum TIM_DAPI_ONLY {
            description
              "Only checks for DAPI mismatch";
          }
          enum TIM_SAPI_DAPI {
            description
              "Checks for SAPI and DAPI mismatch";
          }
        }
        description
          "The Trail Trace Identifier Mismatch (TIM) controls checking for Trace Identifier Mismatch fault detection. ";
        config true;
      }
      leaf dm-enable {
        yang:create-supported "true";
        yang:get-supported "true";
        yang:edit-supported "true";
        yang:delete-supported "false";
        type enumeration {
          enum YES;
          enum NO;
        }
        default "NO";
        description
          "Specify if delay measurement is enable.";
        config true;
      }
      leaf degm-intv {
        default "2";
        yang:create-supported "true";
        yang:get-supported "true";
        yang:edit-supported "true";
        yang:delete-supported "false";
        type ciena-6500-types:INT {
          range "2..10";
        }
        description
          "Consecutive bad intervals required to declare signal degrade";
        config true;
      }
      leaf degthr-percentage {
        default "100";
        yang:create-supported "true";
        yang:get-supported "true";
        yang:edit-supported "true";
        yang:delete-supported "false";
        type ciena-6500-types:INT {
          range "1..1000";
        }
        description
          "Percentage of errored blocks required to declare an interval bad";
        config true;
      }
      leaf tcm-condtype {
        default "NONE";
        yang:create-supported "true";
        yang:get-supported "true";
        yang:edit-supported "true";
        yang:delete-supported "false";
        type ciena-6500-enums:tcmCondType;
        description
          "TCM/PM layer on-ramp conditioning control";
        config true;
      }
      leaf rxcondhold-off {
        default "0";
        yang:create-supported "true";
        yang:get-supported "true";
        yang:edit-supported "true";
        yang:delete-supported "false";
        type ciena-6500-types:INT {
          range "0 | 10 | 20 | 30 | 40 | 50 | 60 | 70 | 80 | 90 | 100 | 200 | 300 | 400 | 500 | 600 | 700 | 800 | 900 | 1000";
        }
        description
          "Signal Conditioning holdoff duration (for Cascaded TPT)";
        config true;
      }
      leaf-list tcm-rxcondtrig {
        yang:create-supported "true";
        yang:get-supported "true";
        yang:edit-supported "true";
        yang:delete-supported "false";
        type ciena-6500-enums:rxCondTrig;
        description
          "Determines if Plug Fail/Card Fail and xTTP Port OOS trigger on-ramp conditioning";
        config true;
      }
      leaf tcm-ltcactmode {
        default "OFF";
        yang:create-supported "true";
        yang:get-supported "true";
        yang:edit-supported "true";
        yang:delete-supported "false";
        type ciena-6500-enums:ltcActMode;
        description
          "Control the conditioning and switching sequence action";
        config true;
      }
      leaf tcm-ltcalmmode {
        default "ON";
        yang:create-supported "true";
        yang:get-supported "true";
        yang:edit-supported "true";
        yang:delete-supported "false";
        type ciena-6500-enums:ltcAlmMode;
        description
          "Enable or disable alarming for LTC fault";
        config true;
      }
      leaf tf-mode {
        yang:create-supported "true";
        yang:get-supported "true";
        yang:edit-supported "true";
        yang:delete-supported "false";
        type ciena-6500-enums:otntfMode;
        default "OFF";
        description
          "Trace Fail Mode";
        config true;
      }
      leaf tcm-txcondtype {
        yang:create-supported "true";
        yang:get-supported "true";
        yang:edit-supported "true";
        yang:delete-supported "false";
        type ciena-6500-enums:txCondType;
        description
          "Tx Action against Tx faults";
        config true;
      }
      leaf pst {
        yang:create-supported "true";
        yang:get-supported "true";
        yang:edit-supported "false";
        yang:delete-supported "false";
        type enumeration {
          enum IS {
            description
              "In Service(This value can be used in create operation)";
          }
          enum OOS-MA {
            description
              "Out-of-service maintenance for provisioning memory administration(This value can be used in create operation)";
          }
          enum IS-ANR {
            description
              "In Service - Abnormal";
          }
          enum OOS-AU {
            description
              "Out-of-service autonomous from a failure detected point of view. It is not out of service from a state point of view. Alarm is raised if the entity is not able to perform its provisioned functions";
          }
          enum OOS-AUMA {
            description
              "Out-of-service autonomous management - the entity is not able to perform its provisioned functions and is purposefully removed from service";
          }
          enum OOS-MAANR {
            description
              "Out-of-service maintenance - abnormal.";
          }
        }
        description
          "Identify the primary state";
        config true;
      }
      leaf-list sst {
        yang:create-supported "true";
        yang:get-supported "true";
        yang:edit-supported "true";
        yang:delete-supported "false";
        type enumeration {
          enum AINS {
            description
              "Auto-In-Service(This value can be used in create and edit operations)";
          }
          enum AINS-DEA {
            description
              "Auto-In-Service Deactivate(This value can be used in create and edit operations)";
          }
          enum BRIDGED {
            description
              "Transition from switched to bridged";
          }
          enum SWITCHED {
            description
              "Transition from bridged to switched";
          }
          enum ROLL;
          enum ACT;
          enum IDLE;
          enum STBYS;
          enum WRK;
          enum ERRANL;
          enum PSI;
          enum FLT;
          enum MEA;
          enum TSTF;
          enum UEQ;
          enum SGEO;
          enum DISCD;
          enum LPBK;
          enum TS;
          enum FAF;
          enum STBYH;
          enum WRKRX;
          enum WRKTX;
          enum PRTCL;
          enum UAS;
          enum NOSITE;
          enum NOAM;
          enum MON;
          enum MSC;
          enum PROTECTED;
          enum MT {
            description
              "Maintenance(This value can be used in create operation)";
          }
          enum DSBLD;
          enum INHIP;
          enum L2DSBLD;
          enum TSGEN;
          enum TSMON;
          enum TSRECIRC;
          enum TSTIP;
          enum TSTCOMPLD;
          enum TS-DEA;
        }
        description
          "Identify the secondary state";
        config true;
      }
      leaf rx-sapi {
        yang:create-supported "false";
        yang:get-supported "true";
        yang:edit-supported "false";
        yang:delete-supported "false";
        type string {
          length "0..15";
        }
        description
          "The Source Access Point Identifier (SAPI) recovered from the Trail Trace Identifier (TTI) overhead position at the sink of a trail.";
        config false;
      }
      leaf rx-dapi {
        yang:create-supported "false";
        yang:get-supported "true";
        yang:edit-supported "false";
        yang:delete-supported "false";
        type string {
          length "0..15";
        }
        description
          "The Destination Access Point Identifier (DAPI) recovered from the Trail Trace Identifier (TTI) overhead position at the sink of a trail.";
        config false;
      }
      leaf rx-oper {
        yang:create-supported "false";
        yang:get-supported "true";
        yang:edit-supported "false";
        yang:delete-supported "false";
        type string {
          length "0..32";
        }
        description
          "The operator specific part of the Trail Trace Identifier (TTI) information, recovered from the TTI overhead position at the sink of a trail.";
        config false;
      }
      leaf dm-count {
        yang:create-supported "false";
        yang:get-supported "true";
        yang:edit-supported "false";
        yang:delete-supported "false";
        type ciena-6500-types:STRING;
        description
          "Value of delay measurement in micro seconds.";
        config false;
      }
      leaf owner {
        yang:create-supported "false";
        yang:get-supported "true";
        yang:edit-supported "false";
        yang:delete-supported "false";
        type ciena-6500-enums:Owner;
        description
          "Specifies who created this facility.";
        config false;
      }
      leaf supported-term-pt {
        yang:create-supported "false";
        yang:get-supported "true";
        yang:edit-supported "false";
        yang:delete-supported "false";
        type ciena-6500-types:aid;
        description
          "The supporting Termination Point.";
        config false;
      }
      leaf ains-time-left {
        yang:create-supported "false";
        yang:get-supported "true";
        yang:edit-supported "false";
        yang:delete-supported "false";
        type ciena-6500-types:TIME;
        description
          "The format will be HH-MM for the time left in AINS timeout.";
        config false;
      }
      leaf rx-mon {
        yang:create-supported "false";
        yang:get-supported "true";
        yang:edit-supported "false";
        yang:delete-supported "false";
        type ciena-6500-enums:BOOL_YES_NO_defaultNO;
        description
          "Indicate if the signal is monitored in the Rx direction for alarms and PMs and OMs.";
        config false;
      }
      leaf rx-term {
        yang:create-supported "false";
        yang:get-supported "true";
        yang:edit-supported "false";
        yang:delete-supported "false";
        type ciena-6500-enums:BOOL_YES_NO_defaultNO;
        description
          "Indicate if the signal is terminated in the Rx direction or not.";
        config false;
      }
      leaf tx-mon {
        yang:create-supported "false";
        yang:get-supported "true";
        yang:edit-supported "false";
        yang:delete-supported "false";
        type ciena-6500-enums:BOOL_YES_NO_defaultNO;
        description
          "Indicate if the signal is monitored in the Tx direction for alarms and PMs and OMs.";
        config false;
      }
      leaf tx-term {
        yang:create-supported "false";
        yang:get-supported "true";
        yang:edit-supported "false";
        yang:delete-supported "false";
        type ciena-6500-enums:BOOL_YES_NO_defaultNO;
        description
          "Indicate if the signal is terminated in the Tx direction for alarms and PMs and OMs.";
        config false;
      }
    }
    list cbrttp {
      yang:handler "tl1";
      yang:create-supported "true";
      yang:get-supported "true";
      yang:edit-supported "true";
      yang:delete-supported "true";
      key "cbrttp";
      config true;
      leaf cbrttp {
        mandatory true;
        description
          "AID in format CBRTTP-shelf-slot-port, CBRTTP-shelf-slot-ALL, CBRTTP-shelf-ALL, ALL";
        type ciena-6500-types:aid;
      }
      leaf rate {
        yang:create-supported "true";
        yang:get-supported "true";
        yang:edit-supported "false";
        yang:delete-supported "false";
        type string {
          length "0..10";
        }
        description
          "User specified Rate";
        config true;
      }
      leaf protocol {
        yang:create-supported "true";
        yang:get-supported "true";
        yang:edit-supported "false";
        yang:delete-supported "false";
        type ciena-6500-enums:CbrTtpProtocol;
        description
          "";
        config true;
      }
      leaf an {
        default "ON";
        yang:create-supported "true";
        yang:get-supported "true";
        yang:edit-supported "true";
        yang:delete-supported "false";
        type ciena-6500-enums:AUTO_NEGOTIATION;
        description
          "Indicating whether to perform speed Auto-negotiation";
        config true;
      }
      leaf label {
        yang:create-supported "true";
        yang:get-supported "true";
        yang:edit-supported "true";
        yang:delete-supported "false";
        type string {
          length "0..64";
        }
        description
          "User specified Label";
        config true;
      }
      leaf mapping {
        yang:create-supported "true";
        yang:get-supported "true";
        yang:edit-supported "true";
        yang:delete-supported "false";
        type ciena-6500-enums:CbrMapping;
        description
          "Defines the mapping of this facility and the children that it will have.";
        config true;
      }
      leaf hold-off {
        default "100";
        yang:create-supported "true";
        yang:get-supported "true";
        yang:edit-supported "true";
        yang:delete-supported "false";
        type ciena-6500-types:INT {
          range "0 | 10 | 20 | 30 | 40 | 50 | 60 | 70 | 80 | 90 | 100 | 200 | 300 | 400 | 500 | 600 | 700 | 800 | 900 | 1000";
        }
        description
          "Conditioning holdoff time in seconds.";
        config true;
      }
      leaf fec-frmt {
        yang:create-supported "true";
        yang:get-supported "true";
        yang:edit-supported "true";
        yang:delete-supported "false";
        type ciena-6500-enums:CbrFECFrmt;
        description
          "FEC Format";
        config true;
      }
      leaf pre-fec-sf-th-lev {
        default "0.00";
        yang:create-supported "true";
        yang:get-supported "true";
        yang:edit-supported "true";
        yang:delete-supported "false";
        type decimal64 {
          range "-1.00..1.00";
          fraction-digits 2;
        }
        description
          "Pre-FEC Signal Fail Threshold";
        config true;
      }
      leaf pre-fec-sd-th-lev {
        default "0.50";
        yang:create-supported "true";
        yang:get-supported "true";
        yang:edit-supported "true";
        yang:delete-supported "false";
        type decimal64 {
          range "-1.00..2.00";
          fraction-digits 2;
        }
        description
          "Pre-FEC Signal Degrade Threshold";
        config true;
      }
      leaf cond-type {
        yang:create-supported "true";
        yang:get-supported "true";
        yang:edit-supported "true";
        yang:delete-supported "false";
        type ciena-6500-enums:CbrTtpCondType;
        description
          "Specifies ethernet specific client conditioning behaviour.";
        config true;
      }
      leaf pst {
        yang:create-supported "true";
        yang:get-supported "true";
        yang:edit-supported "false";
        yang:delete-supported "false";
        type enumeration {
          enum IS {
            description
              "In Service(This value can be used in create operation)";
          }
          enum OOS-MA {
            description
              "Out-of-service maintenance for provisioning memory administration(This value can be used in create operation)";
          }
          enum IS-ANR {
            description
              "In Service - Abnormal";
          }
          enum OOS-AU {
            description
              "Out-of-service autonomous from a failure detected point of view. It is not out of service from a state point of view. Alarm is raised if the entity is not able to perform its provisioned functions";
          }
          enum OOS-AUMA {
            description
              "Out-of-service autonomous management - the entity is not able to perform its provisioned functions and is purposefully removed from service";
          }
          enum OOS-MAANR {
            description
              "Out-of-service maintenance - abnormal.";
          }
        }
        description
          "Identify the primary state";
        config true;
      }
      leaf supported-term-pt {
        yang:create-supported "false";
        yang:get-supported "true";
        yang:edit-supported "false";
        yang:delete-supported "false";
        type ciena-6500-types:aid;
        description
          "The supporting Termination Point.";
        config false;
      }
      leaf pre-fec-sf-th-ber {
        default "0.0";
        yang:create-supported "false";
        yang:get-supported "true";
        yang:edit-supported "false";
        yang:delete-supported "false";
        type ciena-6500-types:STRING;
        description
          "The corresponding BER for a given Pre-FEC SF Threshold setting in dDQ";
        config false;
      }
      leaf pre-fec-sd-th-ber {
        default "0.0";
        yang:create-supported "false";
        yang:get-supported "true";
        yang:edit-supported "false";
        yang:delete-supported "false";
        type ciena-6500-types:STRING;
        description
          "The corresponding BER for a given Pre-FEC SD Threshold setting in dDQ";
        config false;
      }
      leaf-list sst {
        yang:create-supported "false";
        yang:get-supported "true";
        yang:edit-supported "false";
        yang:delete-supported "false";
        type ciena-6500-enums:SSTfac;
        description
          "Secondary State";
        config false;
      }
    }
    list pdh {
      yang:handler "tl1";
      yang:create-supported "true";
      yang:get-supported "true";
      yang:edit-supported "true";
      yang:delete-supported "true";
      key "pdh";
      config true;
      leaf pdh {
        mandatory true;
        description
          "AID in format PDH-shelf-slot-port-rt1Ptp1-rt2Ptp2, PDH-shelf-slot-port-rt1Ptp1-rt2Ptp2-rt3Ptp3, PDH-shelf-slot-port-rt1Ptp1-rt2Ptp2-rt3Ptp3-rt4Ptp4, PDH-shelf-slot-port-rt1Ptp1-rt2Ptp2-rt3Ptp3-rt4Ptp4-rt5Ptp5, PDH-shelf-slotSsubslot-port-rt1Ptp1, PDH-shelf-slotSsubslot-port-rt1Ptp1-rt2Ptp2, PDH-shelf-slotSsubslot-port-rt1Ptp1-rt2Ptp2-rt3Ptp3, PDH-shelf-slotSsubslot-port-rt1Ptp1-rt2Ptp2-rt3Ptp3-rt4Ptp4, PDH-shelf-slot-port-rt1Ptp1, PDH-shelf-slot-ALL, PDH-shelf-slot-port-ALL, PDH-shelf-slotSsubslot-ALL, PDH-shelf-slotSsubslot-port-ALL, PDH-shelf-ALL, ALL";
        type ciena-6500-types:aid;
      }
      leaf frame-fmt {
        yang:create-supported "true";
        yang:get-supported "true";
        yang:edit-supported "true";
        yang:delete-supported "false";
        type ciena-6500-enums:frmfmt;
        description
          "Frame Format";
        config true;
      }
      leaf label {
        yang:create-supported "true";
        yang:get-supported "true";
        yang:edit-supported "true";
        yang:delete-supported "false";
        type string {
          length "0..64";
        }
        description
          "User specified Label";
        config true;
      }
      leaf rx-mon {
        yang:create-supported "true";
        yang:get-supported "true";
        yang:edit-supported "true";
        yang:delete-supported "false";
        type ciena-6500-enums:BOOL_YES_NO_defaultNO;
        default "NO";
        description
          "Indicate if the signal is monitored in the Rx direction for alarms and PMs and OMs.";
        config true;
      }
      leaf rx-term {
        yang:create-supported "true";
        yang:get-supported "true";
        yang:edit-supported "true";
        yang:delete-supported "false";
        type ciena-6500-enums:BOOL_YES_NO_defaultNO;
        mandatory true;
        description
          "Indicate if the signal is terminated in the Rx direction or not.";
        config true;
      }
      leaf tx-mon {
        yang:create-supported "true";
        yang:get-supported "true";
        yang:edit-supported "true";
        yang:delete-supported "false";
        type ciena-6500-enums:BOOL_YES_NO_defaultNO;
        default "NO";
        description
          "Indicate if the signal is monitored in the Tx direction for alarms and PMs and OMs.";
        config true;
      }
      leaf ais_rpt {
        yang:create-supported "true";
        yang:get-supported "true";
        yang:edit-supported "true";
        yang:delete-supported "false";
        type ciena-6500-enums:BOOL_ON_OFF_defaultOFF;
        default "OFF";
        description
          "AIS alarm reporting control. Indicates if the facility AIS alarm reporting is On or Off. The value of Off will prevent the AIS alarm from being raised. Default value comes from the system parameter AIS Reporting Default.";
        config true;
      }
      leaf rai_rpt {
        yang:create-supported "true";
        yang:get-supported "true";
        yang:edit-supported "true";
        yang:delete-supported "false";
        type ciena-6500-enums:BOOL_ON_OFF_defaultOFF;
        default "OFF";
        description
          "RAI alarm reporting control. Indicates if the facility RAI alarm reporting is On or Off. The value of Off will prevent the RAI alarm from being raised. Default value comes from the system parameter RFI RAI Reporting Default.";
        config true;
      }
      leaf summary-contrib {
        yang:create-supported "true";
        yang:get-supported "true";
        yang:edit-supported "true";
        yang:delete-supported "false";
        type ciena-6500-enums:BOOL_ON_OFF_defaultON;
        default "ON";
        description
          "Controls if the facility contributes to summary alarm or summary event.";
        config true;
      }
      leaf pst {
        yang:create-supported "true";
        yang:get-supported "true";
        yang:edit-supported "false";
        yang:delete-supported "false";
        type enumeration {
          enum IS {
            description
              "In Service(This value can be used in create operation)";
          }
          enum OOS-MA {
            description
              "Out-of-service maintenance for provisioning memory administration(This value can be used in create operation)";
          }
          enum IS-ANR {
            description
              "In Service - Abnormal";
          }
          enum OOS-AU {
            description
              "Out-of-service autonomous from a failure detected point of view. It is not out of service from a state point of view. Alarm is raised if the entity is not able to perform its provisioned functions";
          }
          enum OOS-AUMA {
            description
              "Out-of-service autonomous management - the entity is not able to perform its provisioned functions and is purposefully removed from service";
          }
          enum OOS-MAANR {
            description
              "Out-of-service maintenance - abnormal.";
          }
        }
        description
          "Identify the primary state";
        config true;
      }
      leaf-list sst {
        yang:create-supported "true";
        yang:get-supported "true";
        yang:edit-supported "true";
        yang:delete-supported "false";
        type enumeration {
          enum TS {
            description
              "Test Access(This value can be used in create and edit operations)";
          }
          enum TS-DEA {
            description
              "Test Access Deactivate(This value can be used in create and edit operations)";
          }
          enum MT {
            description
              "Maintenance(This value can be used in create and edit operations)";
          }
          enum AINS {
            description
              "Auto-In-Service";
          }
          enum FLT;
          enum LPBK;
          enum SGEO;
          enum TSGEN;
          enum TSMON;
        }
        description
          "Identify the secondary state";
        config true;
      }
      leaf rate {
        yang:create-supported "false";
        yang:get-supported "true";
        yang:edit-supported "false";
        yang:delete-supported "false";
        type ciena-6500-enums:PtsTtpPdhRate;
        description
          "Rate";
        config false;
      }
      leaf far-end-nte {
        yang:create-supported "false";
        yang:get-supported "true";
        yang:edit-supported "false";
        yang:delete-supported "false";
        type ciena-6500-enums:DS1_NTE;
        description
          "Far End NE Type";
        config false;
      }
      leaf fault-loc-mode {
        yang:create-supported "false";
        yang:get-supported "true";
        yang:edit-supported "false";
        yang:delete-supported "false";
        type ciena-6500-enums:DS1_FLMDE;
        description
          "Fault Locate Mode";
        config false;
      }
      leaf map {
        yang:create-supported "false";
        yang:get-supported "true";
        yang:edit-supported "false";
        yang:delete-supported "false";
        type ciena-6500-enums:DS1_MAP;
        description
          "Mapping Type";
        config false;
      }
      leaf out-mode {
        yang:create-supported "false";
        yang:get-supported "true";
        yang:edit-supported "false";
        yang:delete-supported "false";
        type ciena-6500-enums:DS1_OMODE;
        description
          "Outgoing Mode";
        config false;
      }
      leaf supported-term-pt {
        yang:create-supported "false";
        yang:get-supported "true";
        yang:edit-supported "false";
        yang:delete-supported "false";
        type ciena-6500-types:aid;
        description
          "The supporting Termination Point.";
        config false;
      }
      leaf tx-term {
        yang:create-supported "false";
        yang:get-supported "true";
        yang:edit-supported "false";
        yang:delete-supported "false";
        type ciena-6500-enums:BOOL_YES_NO_defaultNO;
        description
          "Indicate if the signal is terminated in the Tx direction for alarms and PMs and OMs.";
        config false;
      }
      leaf usage {
        yang:create-supported "false";
        yang:get-supported "true";
        yang:edit-supported "false";
        yang:delete-supported "false";
        type ciena-6500-enums:ptsPDHUsage;
        description
          "Indicate if this PATH can be cross-connected or what child facility can be created.";
        config false;
      }
    }
    list path {
      yang:handler "tl1";
      yang:create-supported "true";
      yang:get-supported "true";
      yang:edit-supported "true";
      yang:delete-supported "true";
      key "path";
      config true;
      leaf path {
        mandatory true;
        description
          "AID in format PATH-shelf-slot-port-rt1Ptp1, PATH-shelf-slot-port-rt1Ptp1-rt2Ptp2, PATH-shelf-slot-port-rt1Ptp1-rt2Ptp2-rt3Ptp3, PATH-shelf-slot-port-rt1Ptp1-rt2Ptp2-rt3Ptp3-rt4Ptp4, PATH-shelf-slotSsubslot-port-rt1Ptp1, PATH-shelf-slotSsubslot-port-rt1Ptp1-rt2Ptp2-rt3Ptp3, PATH-shelf-slot-ALL, PATH-shelf-slot-port-ALL, PATH-shelf-slotSsubslot-ALL, PATH-shelf-slotSsubslot-port-ALL, PATH-shelf-ALL, ALL";
        type ciena-6500-types:aid;
      }
      leaf trc-format {
        yang:create-supported "true";
        yang:get-supported "true";
        yang:edit-supported "true";
        yang:delete-supported "false";
        type ciena-6500-enums:trcFormat;
        description
          "TRC Format";
        config true;
      }
      leaf exp-path-trace {
        yang:create-supported "true";
        yang:get-supported "true";
        yang:edit-supported "true";
        yang:delete-supported "false";
        type string {
          length "1..62";
        }
        description
          "Expected path trace: 15 characters when TRCFORMAT is 16BYTE, 62 characters when TRCFORMAT is 64BYTE";
        config true;
      }
      leaf out-path-trace {
        yang:create-supported "true";
        yang:get-supported "true";
        yang:edit-supported "true";
        yang:delete-supported "false";
        type string {
          length "1..62";
        }
        description
          "Outgoing path trace: 15 characters when TRCFORMAT is 16BYTE, 62 characters when TRCFORMAT is 64BYTE";
        config true;
      }
      leaf tf-mode {
        yang:create-supported "true";
        yang:get-supported "true";
        yang:edit-supported "true";
        yang:delete-supported "false";
        type ciena-6500-enums:pathtfMode;
        default "OFF";
        description
          "Trace Fail Mode";
        config true;
      }
      leaf label {
        yang:create-supported "true";
        yang:get-supported "true";
        yang:edit-supported "true";
        yang:delete-supported "false";
        type string {
          length "0..64";
        }
        description
          "User specified Label";
        config true;
      }
      leaf rx-mon {
        yang:create-supported "true";
        yang:get-supported "true";
        yang:edit-supported "true";
        yang:delete-supported "false";
        type ciena-6500-enums:BOOL_YES_NO_defaultNO;
        default "NO";
        description
          "Indicate if the signal is monitored in the Rx direction for alarms and PMs and OMs.";
        config true;
      }
      leaf rx-term {
        yang:create-supported "true";
        yang:get-supported "true";
        yang:edit-supported "true";
        yang:delete-supported "false";
        type ciena-6500-enums:BOOL_YES_NO_defaultNO;
        mandatory true;
        description
          "Indicate if the signal is terminated in the Rx direction or not.";
        config true;
      }
      leaf tx-mon {
        yang:create-supported "true";
        yang:get-supported "true";
        yang:edit-supported "true";
        yang:delete-supported "false";
        type ciena-6500-enums:BOOL_YES_NO_defaultNO;
        default "NO";
        description
          "Indicate if the signal is monitored in the Tx direction for alarms and PMs and OMs.";
        config true;
      }
      leaf ais_rpt {
        yang:create-supported "true";
        yang:get-supported "true";
        yang:edit-supported "true";
        yang:delete-supported "false";
        type ciena-6500-enums:BOOL_ON_OFF_defaultOFF;
        default "OFF";
        description
          "AIS alarm reporting control. Indicates if the facility AIS alarm reporting is On or Off. The value of Off will prevent the AIS alarm from being raised. Default value comes from the system parameter AIS Reporting Default.";
        config true;
      }
      leaf rfi_rpt {
        yang:create-supported "true";
        yang:get-supported "true";
        yang:edit-supported "true";
        yang:delete-supported "false";
        type ciena-6500-enums:BOOL_ON_OFF_defaultOFF;
        default "OFF";
        description
          "RFI alarm reporting control. Indicates if the facility RFI alarm reporting is On or Off. The value of Off will prevent the RFI alarm from being raised. Default value comes from the system parameter RFI RAI Reporting Default.";
        config true;
      }
      leaf summary-contrib {
        yang:create-supported "true";
        yang:get-supported "true";
        yang:edit-supported "true";
        yang:delete-supported "false";
        type ciena-6500-enums:BOOL_ON_OFF_defaultON;
        default "ON";
        description
          "Controls if the facility contributes to summary alarm or summary event.";
        config true;
      }
      leaf usage {
        yang:create-supported "true";
        yang:get-supported "true";
        yang:edit-supported "true";
        yang:delete-supported "false";
        type ciena-6500-enums:ptsMROUsage;
        mandatory true;
        description
          "Indicate if this PATH can be cross-connected or what child facility can be created.";
        config true;
      }
      leaf pst {
        yang:create-supported "true";
        yang:get-supported "true";
        yang:edit-supported "false";
        yang:delete-supported "false";
        type enumeration {
          enum IS {
            description
              "In Service(This value can be used in create operation)";
          }
          enum OOS-MA {
            description
              "Out-of-service maintenance for provisioning memory administration(This value can be used in create operation)";
          }
          enum IS-ANR {
            description
              "In Service - Abnormal";
          }
          enum OOS-AU {
            description
              "Out-of-service autonomous from a failure detected point of view. It is not out of service from a state point of view. Alarm is raised if the entity is not able to perform its provisioned functions";
          }
          enum OOS-AUMA {
            description
              "Out-of-service autonomous management - the entity is not able to perform its provisioned functions and is purposefully removed from service";
          }
          enum OOS-MAANR {
            description
              "Out-of-service maintenance - abnormal.";
          }
        }
        description
          "Identify the primary state";
        config true;
      }
      leaf-list sst {
        yang:create-supported "true";
        yang:get-supported "true";
        yang:edit-supported "true";
        yang:delete-supported "false";
        type enumeration {
          enum MT {
            description
              "Maintenance(This value can be used in create and edit operations)";
          }
          enum AINS {
            description
              "Auto-In-Service";
          }
          enum DISCD;
          enum FLT;
          enum LPBK;
          enum SGEO;
          enum STBYH;
          enum TSGEN;
          enum TSMON;
          enum WRKRX;
        }
        description
          "Identify the secondary state";
        config true;
      }
      leaf exp-sig-label {
        yang:create-supported "false";
        yang:get-supported "true";
        yang:edit-supported "false";
        yang:delete-supported "false";
        type ciena-6500-types:INT {
          range "0..4";
        }
        description
          "Expected signal label";
        config false;
      }
      leaf in-sig-label {
        yang:create-supported "false";
        yang:get-supported "true";
        yang:edit-supported "false";
        yang:delete-supported "false";
        type union {
          type enumeration {
            enum UNKNOWN;
          }
          type ciena-6500-types:INT {
            range "1..4";
          }
        }
        description
          "Incoming signal label";
        config false;
      }
      leaf out-sig-label {
        yang:create-supported "false";
        yang:get-supported "true";
        yang:edit-supported "false";
        yang:delete-supported "false";
        type ciena-6500-types:INT {
          range "0..4";
        }
        description
          "Outgoing signal label";
        config false;
      }
      leaf in-path-trace {
        yang:create-supported "false";
        yang:get-supported "true";
        yang:edit-supported "false";
        yang:delete-supported "false";
        type string {
          length "1..62";
        }
        description
          "Incoming path trace: 15 characters when TRCFORMAT is 16BYTE, 62 characters when TRCFORMAT is 64BYTE";
        config false;
      }
      leaf rate {
        yang:create-supported "false";
        yang:get-supported "true";
        yang:edit-supported "false";
        yang:delete-supported "false";
        type ciena-6500-enums:PtsTtpPathRate;
        description
          "Rate";
        config false;
      }
      leaf supported-term-pt {
        yang:create-supported "false";
        yang:get-supported "true";
        yang:edit-supported "false";
        yang:delete-supported "false";
        type ciena-6500-types:aid;
        description
          "The supporting Termination Point.";
        config false;
      }
      leaf tx-term {
        yang:create-supported "false";
        yang:get-supported "true";
        yang:edit-supported "false";
        yang:delete-supported "false";
        type ciena-6500-enums:BOOL_YES_NO_defaultNO;
        description
          "Indicate if the signal is terminated in the Tx direction for alarms and PMs and OMs.";
        config false;
      }
    }
    list pktiwf {
      yang:handler "tl1";
      yang:create-supported "true";
      yang:get-supported "true";
      yang:edit-supported "true";
      yang:delete-supported "true";
      key "pktiwf";
      config true;
      leaf pktiwf {
        mandatory true;
        description
          "AID in format PKTIWF-shelf-slot-iwfid, PKTIWF-shelf-slotSsubslot-iwfid, PKTIWF-shelf-slot-ALL, PKTIWF-shelf-slotSsubslot-ALL, PKTIWF-shelf-ALL, ALL";
        type ciena-6500-types:aid;
      }
      leaf cas {
        yang:create-supported "true";
        yang:get-supported "true";
        yang:edit-supported "true";
        yang:delete-supported "false";
        type ciena-6500-enums:BOOL_ON_OFF_defaultOFF;
        default "OFF";
        description
          "Channel Associated Signaling";
        config true;
      }
      leaf clk-rec-mode {
        yang:create-supported "true";
        yang:get-supported "true";
        yang:edit-supported "true";
        yang:delete-supported "false";
        type ciena-6500-enums:clkRecoveryMode;
        description
          "Clock Recovery Mode, default is adaptive";
        config true;
      }
      leaf ds0-map {
        yang:create-supported "true";
        yang:get-supported "true";
        yang:edit-supported "true";
        yang:delete-supported "false";
        type ciena-6500-types:STRING;
        description
          "DS0MAP";
        config true;
      }
      leaf jitter-buffer-depth {
        yang:create-supported "true";
        yang:get-supported "true";
        yang:edit-supported "true";
        yang:delete-supported "false";
        type ciena-6500-types:INT {
          range "1..32";
        }
        description
          "Jitter Buffer Depth in milliseconds in 1 msec increments.";
        config true;
      }
      leaf label {
        yang:create-supported "true";
        yang:get-supported "true";
        yang:edit-supported "true";
        yang:delete-supported "false";
        type string {
          length "0..64";
        }
        description
          "User Specified Label";
        config true;
      }
      leaf mapping {
        yang:create-supported "true";
        yang:get-supported "true";
        yang:edit-supported "true";
        yang:delete-supported "false";
        type ciena-6500-enums:PktiwfMapping;
        mandatory true;
        description
          "Packet Mapping. CEP (i.e. MPLS), MEF3 (i.e. Ethernet), MEF8 (i.e. Ethernet), SATOP (i.e. MPLS), CESOPSN.";
        config true;
      }
      leaf out-payload-type {
        default "0";
        yang:create-supported "true";
        yang:get-supported "true";
        yang:edit-supported "true";
        yang:delete-supported "false";
        type ciena-6500-types:INT {
          range "0..127";
        }
        description
          "Outgoing TX RTP Header Payload Type towards the fabric. 7 bit integer (0..127) with values as described in MEF8 and defined here: http://www.iana.org/assignments/rtp-parameters/rtp-parameters.xhtml";
        config true;
      }
      leaf out-sync-src {
        default "0";
        yang:create-supported "true";
        yang:get-supported "true";
        yang:edit-supported "true";
        yang:delete-supported "false";
        type ciena-6500-types:INT {
          range "0..4294967295";
        }
        description
          "Outgoing RTP Header Synchronization Source towards the fabric. 32 bit integer (0..4294967295)";
        config true;
      }
      leaf ptr-proc-mode {
        yang:create-supported "true";
        yang:get-supported "true";
        yang:edit-supported "true";
        yang:delete-supported "false";
        type ciena-6500-enums:ptrProcessingMode;
        default "EPAR";
        description
          "Pointer Processing Mode";
        config true;
      }
      leaf rtp-header {
        yang:create-supported "true";
        yang:get-supported "true";
        yang:edit-supported "true";
        yang:delete-supported "false";
        type ciena-6500-enums:BOOL_YES_NO_defaultNO;
        default "NO";
        description
          "Indicates whether to include the RTP Header";
        config true;
      }
      leaf tx-mon {
        yang:create-supported "true";
        yang:get-supported "true";
        yang:edit-supported "true";
        yang:delete-supported "false";
        type ciena-6500-enums:BOOL_YES_NO_defaultNO;
        default "NO";
        description
          "Indicates if signal is monitored in TX direction for alarms and PMs";
        config true;
      }
      leaf supported-term-pt {
        yang:create-supported "true";
        yang:get-supported "true";
        yang:edit-supported "false";
        yang:delete-supported "false";
        type ciena-6500-types:aid;
        mandatory true;
        description
          "Supporting Termination Point";
        config true;
      }
      leaf summary-contrib {
        yang:create-supported "true";
        yang:get-supported "true";
        yang:edit-supported "true";
        yang:delete-supported "false";
        type ciena-6500-enums:BOOL_ON_OFF_defaultON;
        default "ON";
        description
          "Controls if the facility contributes to summary alarm or summary event.";
        config true;
      }
      leaf abcd1 {
        yang:create-supported "true";
        yang:get-supported "true";
        yang:edit-supported "true";
        yang:delete-supported "false";
        type string {
          length "1";
        }
        description
          "Specifies the ABCD1 conditioning code to be used in the signaling bits of a DS0. This attribute is only applicable on cards which have the enhanced DS0 support enabled.";
        config true;
      }
      leaf abcd1enable {
        yang:create-supported "true";
        yang:get-supported "true";
        yang:edit-supported "true";
        yang:delete-supported "false";
        type ciena-6500-enums:DISABLE_ENABLE;
        description
          "Indicates if the ABCD1 conditioning codes are enabled or disabled. This attribute is only applicable on cards which have the enhanced DS0 support enabled.";
        config true;
      }
      leaf abcd2 {
        yang:create-supported "true";
        yang:get-supported "true";
        yang:edit-supported "true";
        yang:delete-supported "false";
        type string {
          length "1";
        }
        description
          "Specifies the ABCD2 conditioning code to be used in the signaling bits of a DS0. This attribute is only applicable on cards which have the enhanced DS0 support enabled.";
        config true;
      }
      leaf idlecode {
        yang:create-supported "true";
        yang:get-supported "true";
        yang:edit-supported "true";
        yang:delete-supported "false";
        type string {
          length "1..2";
        }
        description
          " Idle code. Attribute is only applicable on cards which have the enhanced DS0 support enabled.";
        config true;
      }
      leaf pst {
        yang:create-supported "true";
        yang:get-supported "true";
        yang:edit-supported "true";
        yang:delete-supported "false";
        type enumeration {
          enum IS {
            description
              "In Service(This value can be used in create and edit operations)";
          }
          enum OOS-MA {
            description
              "Out-of-service maintenance for provisioning memory administration(This value can be used in create and edit operations)";
          }
          enum IS-ANR {
            description
              "In Service - Abnormal";
          }
          enum OOS-AU {
            description
              "Out-of-service autonomous from a failure detected point of view. It is not out of service from a state point of view. Alarm is raised if the entity is not able to perform its provisioned functions";
          }
          enum OOS-AUMA {
            description
              "Out-of-service autonomous management - the entity is not able to perform its provisioned functions and is purposefully removed from service";
          }
          enum OOS-MAANR {
            description
              "Out-of-service maintenance - abnormal.";
          }
        }
        description
          "Identify the primary state";
        config true;
      }
      leaf-list sst {
        yang:create-supported "true";
        yang:get-supported "true";
        yang:edit-supported "false";
        yang:delete-supported "false";
        type enumeration {
          enum MT {
            description
              "Maintenance(This value can be used in create operation)";
          }
          enum DISCD {
            description
              "Not connected in SAOS";
          }
          enum L2DSBLD {
            description
              "Connected in SAOS but cross connect is disabled";
          }
        }
        description
          "Identify the secondary state";
        config true;
      }
      leaf in-payload-type {
        default "0";
        yang:create-supported "false";
        yang:get-supported "true";
        yang:edit-supported "false";
        yang:delete-supported "false";
        type union {
          type enumeration {
            enum UNKNOWN;
          }
          type ciena-6500-types:INT {
            range "0..127";
          }
        }
        description
          "Incoming RTP Header Payload Type from the fabric. 7 bit integer (0..127) with values as described in MEF8 and defined in http://www.iana.org/assignments/rtp-parameters/rtp-parameters.xhtml.";
        config false;
      }
      leaf in-sync-src {
        default "0";
        yang:create-supported "false";
        yang:get-supported "true";
        yang:edit-supported "false";
        yang:delete-supported "false";
        type union {
          type enumeration {
            enum UNKNOWN;
          }
          type ciena-6500-types:INT {
            range "0..4294967295";
          }
        }
        description
          "Incoming RTP Header Synchronization Source from the fabric. 32 bit integer.";
        config false;
      }
      leaf payload-size {
        yang:create-supported "false";
        yang:get-supported "true";
        yang:edit-supported "false";
        yang:delete-supported "false";
        type ciena-6500-types:INT {
          range "96..4092";
        }
        description
          "Packet Payload Size in bytes";
        config false;
      }
      leaf rate {
        yang:create-supported "false";
        yang:get-supported "true";
        yang:edit-supported "false";
        yang:delete-supported "false";
        type ciena-6500-enums:pktiwfRate;
        description
          "Rate of interworking function";
        config false;
      }
      leaf tx-term {
        yang:create-supported "false";
        yang:get-supported "true";
        yang:edit-supported "false";
        yang:delete-supported "false";
        type ciena-6500-enums:BOOL_YES_NO_defaultYES;
        description
          "Indicates if signal is terminated in TX direction";
        config false;
      }
      leaf abcd2enable {
        yang:create-supported "false";
        yang:get-supported "true";
        yang:edit-supported "false";
        yang:delete-supported "false";
        type ciena-6500-enums:DISABLE_ENABLE;
        description
          "Indicates if the ABCD2 conditioning codes are enabled or disabled. This attribute is only applicable on cards which have the enhanced DS0 support enabled.";
        config false;
      }
      leaf tap1 {
        yang:create-supported "false";
        yang:get-supported "true";
        yang:edit-supported "false";
        yang:delete-supported "false";
        type ciena-6500-types:aid;
        description
          "TAP1";
        config false;
      }
      leaf tap2 {
        yang:create-supported "false";
        yang:get-supported "true";
        yang:edit-supported "false";
        yang:delete-supported "false";
        type ciena-6500-types:aid;
        description
          "TAP2";
        config false;
      }
    }
    list flexi {
      yang:handler "tl1";
      yang:create-supported "true";
      yang:get-supported "true";
      yang:edit-supported "true";
      yang:delete-supported "true";
      key "flexi";
      config true;
      leaf flexi {
        mandatory true;
        description
          "AID in format FLEXI-shelf-slot-port-index, FLEXI-shelf-slot-portSsubport-index, FLEXI-shelf-slot-port, FLEXI-shelf-slot-ALL, FLEXI-shelf-ALL, ALL";
        type ciena-6500-types:aid;
      }
      leaf flexi-type {
        yang:create-supported "true";
        yang:get-supported "true";
        yang:edit-supported "false";
        yang:delete-supported "false";
        type ciena-6500-enums:flexIType;
        description
          "Flexi Type";
        config true;
      }
      leaf tx-gid {
        default "1";
        yang:create-supported "true";
        yang:get-supported "true";
        yang:edit-supported "true";
        yang:delete-supported "false";
        type ciena-6500-types:INT {
          range "1..1048575";
        }
        description
          "Tx Group ID";
        config true;
      }
      leaf tx-iid {
        default "1";
        yang:create-supported "true";
        yang:get-supported "true";
        yang:edit-supported "true";
        yang:delete-supported "false";
        type ciena-6500-types:INT {
          range "1..254";
        }
        description
          "Tx Instance ID";
        config true;
      }
      leaf tx-flexi-map {
        yang:create-supported "true";
        yang:get-supported "true";
        yang:edit-supported "false";
        yang:delete-supported "false";
        type ciena-6500-types:STRING;
        description
          "Tx FLEXI Mapping Bitmap";
        config true;
      }
      leaf role {
        yang:create-supported "true";
        yang:get-supported "true";
        yang:edit-supported "false";
        yang:delete-supported "false";
        type ciena-6500-enums:flexIRole;
        description
          "Role type in OTUCn-M configuration";
        config true;
      }
      leaf p-aid {
        yang:create-supported "true";
        yang:get-supported "true";
        yang:edit-supported "false";
        yang:delete-supported "false";
        type ciena-6500-types:aid;
        description
          "Specify the Prime AID.";
        config true;
      }
      leaf label {
        yang:create-supported "true";
        yang:get-supported "true";
        yang:edit-supported "true";
        yang:delete-supported "false";
        type string {
          length "0..64";
        }
        description
          "User specified Label";
        config true;
      }
      leaf pst {
        yang:create-supported "true";
        yang:get-supported "true";
        yang:edit-supported "true";
        yang:delete-supported "false";
        type enumeration {
          enum IS {
            description
              "In Service(This value can be used in create and edit operations)";
          }
          enum OOS-MA {
            description
              "Out-of-service maintenance for provisioning memory administration(This value can be used in create and edit operations)";
          }
          enum IS-ANR {
            description
              "In Service - Abnormal";
          }
          enum OOS-AU {
            description
              "Out-of-service autonomous from a failure detected point of view. It is not out of service from a state point of view. Alarm is raised if the entity is not able to perform its provisioned functions";
          }
          enum OOS-AUMA {
            description
              "Out-of-service autonomous management - the entity is not able to perform its provisioned functions and is purposefully removed from service";
          }
          enum OOS-MAANR {
            description
              "Out-of-service maintenance - abnormal.";
          }
        }
        description
          "Identify the primary state";
        config true;
      }
      leaf-list sst {
        yang:create-supported "true";
        yang:get-supported "true";
        yang:edit-supported "true";
        yang:delete-supported "false";
        type enumeration {
          enum AINS {
            description
              "Auto-In-Service(This value can be used in create and edit operations)";
          }
          enum AINS-DEA {
            description
              "Auto-In-Service Deactivate(This value can be used in create and edit operations)";
          }
          enum BRIDGED {
            description
              "Transition from switched to bridged";
          }
          enum SWITCHED {
            description
              "Transition from bridged to switched";
          }
          enum ROLL;
          enum ACT;
          enum IDLE;
          enum STBYS;
          enum WRK;
          enum ERRANL;
          enum PSI;
          enum FLT;
          enum MEA;
          enum TSTF;
          enum UEQ;
          enum SGEO;
          enum DISCD;
          enum LPBK;
          enum TS;
          enum FAF;
          enum STBYH;
          enum WRKRX;
          enum WRKTX;
          enum PRTCL;
          enum UAS;
          enum NOSITE;
          enum NOAM;
          enum MON;
          enum MSC;
          enum PROTECTED;
          enum MT {
            description
              "Maintenance(This value can be used in create and edit operations)";
          }
          enum DSBLD;
          enum INHIP;
          enum L2DSBLD;
          enum TSGEN;
          enum TSMON;
          enum TSRECIRC;
          enum TSTIP;
          enum TSTCOMPLD;
          enum TS-DEA;
        }
        description
          "Identify the secondary state";
        config true;
      }
      leaf rx-gid {
        yang:create-supported "false";
        yang:get-supported "true";
        yang:edit-supported "false";
        yang:delete-supported "false";
        type ciena-6500-types:INT {
          range "1..1048575";
        }
        description
          "Rx Group ID";
        config false;
      }
      leaf rx-iid {
        yang:create-supported "false";
        yang:get-supported "true";
        yang:edit-supported "false";
        yang:delete-supported "false";
        type ciena-6500-types:INT {
          range "1..254";
        }
        description
          "Rx Instance ID";
        config false;
      }
      leaf-list m-aid {
        yang:create-supported "false";
        yang:get-supported "true";
        yang:edit-supported "false";
        yang:delete-supported "false";
        type ciena-6500-types:aid;
        description
          "Specify the Member FLEXI AID List. Format: Member2&Member3&...";
        config false;
      }
      leaf rx-flexi-map {
        yang:create-supported "false";
        yang:get-supported "true";
        yang:edit-supported "false";
        yang:delete-supported "false";
        type ciena-6500-types:STRING;
        description
          "Rx FLEXI Mapping Bitmap";
        config false;
      }
      leaf supported-term-pt {
        yang:create-supported "false";
        yang:get-supported "true";
        yang:edit-supported "false";
        yang:delete-supported "false";
        type ciena-6500-types:aid;
        description
          "The supporting Termination Point.";
        config false;
      }
      leaf ains-time-left {
        yang:create-supported "false";
        yang:get-supported "true";
        yang:edit-supported "false";
        yang:delete-supported "false";
        type ciena-6500-types:TIME;
        description
          "The format will be \"HH-MM\" for the time left in AINS timeout.";
        config false;
      }
    }
    list odu {
      yang:handler "tl1";
      yang:create-supported "false";
      yang:get-supported "true";
      yang:edit-supported "true";
      yang:delete-supported "false";
      key "odun";
      config true;
      leaf odun {
        mandatory true;
        description
          "AID in format ODU0-shelf-slot-port-payloadindex, ODU1-shelf-slot-port-payloadindex, ODUFLEX-shelf-slot-port-payloadindex, ODU4-shelf-slot-port-index";
        type ciena-6500-types:aid;
      }
      leaf odu-tx-tti {
        yang:get-supported "true";
        yang:edit-supported "true";
        type ciena-6500-types:STRING;
        description
          "Transmitted ODU TTI 32B. TTI = Trail Trace Identifier";
        config true;
      }
      leaf odu-rx-exp-tti {
        yang:get-supported "true";
        yang:edit-supported "true";
        type ciena-6500-types:STRING;
        description
          "Expected 32 Characters ODU TTI";
        config true;
      }
      leaf odu-tx-sapi {
        yang:get-supported "true";
        yang:edit-supported "true";
        type ciena-6500-types:STRING;
        description
          "ODU Transmitted SAPI TTI (15 Characters). TTI = Trail Trace Identifier";
        config true;
      }
      leaf odu-tx-dapi {
        yang:get-supported "true";
        yang:edit-supported "true";
        type ciena-6500-types:STRING;
        description
          "ODU Transmitted DAPI TTI (15 Characters). TTI = Trail Trace Identifier";
        config true;
      }
      leaf odu-ex-sapi {
        yang:get-supported "true";
        yang:edit-supported "true";
        type ciena-6500-types:STRING;
        description
          "ODU Expected SAPI TTI (15 Characters)";
        config true;
      }
      leaf odu-ex-dapi {
        yang:get-supported "true";
        yang:edit-supported "true";
        type ciena-6500-types:STRING;
        description
          "ODU Expected DAPI TTI (15 Characters)";
        config true;
      }
      leaf odu-tf-mode {
        yang:get-supported "true";
        yang:edit-supported "true";
        type enumeration {
          enum OFF {
            description
              "Alarms off, no traffic protection";
          }
          enum ALMONLY {
            description
              "Alarms on, no traffic protection";
          }
        }
        default "OFF";
        description
          "ODU Trace Fail Mode";
        config true;
      }
      leaf odu-timen {
        yang:get-supported "true";
        yang:edit-supported "true";
        type enumeration {
          enum OPERATOR {
            description
              "Monitor ODU Operator Specific TTI mismatch";
          }
          enum SAPI {
            description
              "Monitor ODU SAPI TTI mismatch";
          }
          enum DAPI {
            description
              "Monitor ODU DAPI TTI mismatch";
          }
          enum SAPI_DAPI {
            description
              "Monitor ODU SAPI and DAPI TTI mismatch";
          }
        }
        default "OPERATOR";
        description
          "ODU TTI Mismatch Detection";
        config true;
      }
      leaf odu-monitor {
        yang:get-supported "true";
        yang:edit-supported "true";
        type enumeration {
          enum NO {
            description
              "ODU Monitoring off";
          }
          enum YES {
            description
              "ODU Monitoring on";
          }
        }
        default "NO";
        description
          "ODU Monitor";
        config true;
      }
      leaf clfi {
        yang:get-supported "true";
        yang:edit-supported "true";
        type ciena-6500-types:STRING;
        description
          "Common Language Facility Identifier. Customer provisionable label for an ODU facility.";
        config true;
      }
      leaf encryption-tcm {
        default "1";
        yang:get-supported "true";
        yang:edit-supported "true";
        type ciena-6500-types:INT {
          range "1..6";
        }
        description
          "Active TCM Level for Encryption";
        config true;
      }
      leaf encr-odu1 {
        yang:get-supported "true";
        yang:edit-supported "true";
        type ciena-6500-types:INT;
        description
          "ODU Reserve Byte 1 for Encryption";
        config true;
      }
      leaf-list sst {
        yang:get-supported "true";
        yang:edit-supported "true";
        type enumeration {
          enum AINS {
            description
              "Auto-In-Service(This value can be used in edit operation)";
          }
          enum AINS-DEA {
            description
              "Auto-In-Service Deactivate(This value can be used in edit operation)";
          }
          enum ACT;
          enum IDLE;
          enum STBYS;
          enum WRK;
          enum FLT;
          enum MEA;
          enum UEQ;
          enum SGEO;
          enum DISCD;
          enum LPBK;
          enum TS;
          enum STBYH;
          enum WRKRX;
          enum WRKTX;
          enum UAS;
          enum PROTECTED;
          enum MT {
            description
              "Maintenance";
          }
          enum DSBLD;
        }
        description
          "Identify the secondary state";
        config true;
      }
      leaf odu-term {
        yang:get-supported "true";
        yang:edit-supported "false";
        type enumeration {
          enum YES {
            description
              "Terminate ODU Layer";
          }
          enum NO {
            description
              "Not terminate ODU Layer";
          }
        }
        description
          "Indicating whether to terminate ODU Layer";
        config false;
      }
      leaf port-mode {
        yang:get-supported "true";
        yang:edit-supported "false";
        type enumeration {
          enum SONET;
          enum SDH;
        }
        description
          "Optical port Market preference";
        config false;
      }
      leaf trib-slot-assignment {
        yang:get-supported "true";
        yang:edit-supported "false";
        type enumeration {
          enum "HEX value 00-FF";
        }
        description
          "This attribute is used to specify the value of transmitted tributary slots.";
        config false;
      }
      leaf ex-ts {
        yang:get-supported "true";
        yang:edit-supported "false";
        type enumeration {
          enum "HEX value 00-FF";
        }
        description
          "This attribute is used to specify the value of expected tributary slots.";
        config false;
      }
      leaf rx-ts {
        yang:get-supported "true";
        yang:edit-supported "false";
        type enumeration {
          enum "HEX value 00-FF";
        }
        description
          "This attribute is used to specify the value of actual received tributary slots.";
        config false;
      }
      leaf trib-slot-prov {
        yang:get-supported "true";
        yang:edit-supported "false";
        type enumeration {
          enum AUTO {
            description
              "The Rx trib slot is auto-detected by system. ";
          }
          enum MANUAL {
            description
              "The Rx trib slot is user specified. ";
          }
        }
        description
          "tribSlots provisioning mode";
        config false;
      }
      leaf odu-flt-mon {
        yang:get-supported "true";
        yang:edit-supported "false";
        type ciena-6500-types:STRING;
        description
          "ODU Fault Monitoring";
        config false;
      }
      leaf odu-prf-mon {
        yang:get-supported "true";
        yang:edit-supported "false";
        type ciena-6500-types:STRING;
        description
          "ODU Performance Monitoring";
        config false;
      }
      leaf ains-time-left {
        yang:get-supported "true";
        yang:edit-supported "false";
        type ciena-6500-types:TIME;
        description
          "The format will be \"HH-MM\" for the time left in AINS timeout.";
        config false;
      }
      leaf pst {
        yang:get-supported "true";
        yang:edit-supported "false";
        type ciena-6500-enums:PSTfac_RTRV;
        description
          "Identify the primary State";
        config false;
      }
    }
    list pc {
      yang:handler "tl1";
      yang:create-supported "false";
      yang:get-supported "true";
      yang:edit-supported "true";
      yang:delete-supported "false";
      key "pc";
      config true;
      leaf pc {
        mandatory true;
        description
          "AID in format PC-shelf-slot-port, PC-shelf-slotSsubslot-port, PC-shelf-ALL, PC-shelf-slot-ALL, PC-shelf-slotSsubslot-ALL, SHELF-shelf-ALL, ALL";
        type ciena-6500-types:aid;
      }
      leaf port-select {
        yang:get-supported "true";
        yang:edit-supported "true";
        type ciena-6500-types:STRING;
        description
          "The provisioned port of the CP to direct traffic towards";
        config true;
      }
      leaf port-label {
        yang:get-supported "true";
        yang:edit-supported "false";
        type ciena-6500-types:STRING;
        description
          "Port Label";
        config false;
      }
      leaf pst {
        yang:get-supported "true";
        yang:edit-supported "false";
        type ciena-6500-enums:PSTfac_RTRV;
        description
          "Identify the primary state";
        config false;
      }
      leaf-list sst {
        yang:get-supported "true";
        yang:edit-supported "false";
        type ciena-6500-enums:SSTfac;
        description
          "Identify the secondary state";
        config false;
      }
    }
    list facgrp {
      yang:handler "tl1";
      yang:create-supported "true";
      yang:get-supported "true";
      yang:edit-supported "true";
      yang:delete-supported "true";
      key "facgrp";
      config true;
      leaf facgrp {
        mandatory true;
        description
          "AID in format FACGRP-shelf-grpIx, FACGRP-shelf-ALL, SHELF-shelf-ALL, ALL";
        type ciena-6500-types:aid;
      }
      leaf service-type {
        yang:create-supported "true";
        yang:get-supported "true";
        yang:edit-supported "true";
        yang:delete-supported "false";
        type ciena-6500-enums:facgrpServiceType;
        mandatory true;
        description
          "Group service";
        config true;
      }
      leaf label {
        yang:create-supported "true";
        yang:get-supported "true";
        yang:edit-supported "true";
        yang:delete-supported "false";
        type string {
          length "0..64";
        }
        description
          "User specified Label";
        config true;
      }
      leaf-list mbrlst {
        yang:create-supported "false";
        yang:get-supported "true";
        yang:edit-supported "false";
        yang:delete-supported "false";
        type ciena-6500-types:aid;
        description
          "List of FACGRP member AIDs.";
        config false;
      }
      leaf minlatency {
        yang:create-supported "false";
        yang:get-supported "true";
        yang:edit-supported "false";
        yang:delete-supported "false";
        type string {
          length "0..64";
        }
        description
          "Minimum latency of the group";
        config false;
      }
      leaf maxlatency {
        yang:create-supported "false";
        yang:get-supported "true";
        yang:edit-supported "false";
        yang:delete-supported "false";
        type string {
          length "0..64";
        }
        description
          "Maximum latency of the group";
        config false;
      }
      leaf pst {
        yang:create-supported "false";
        yang:get-supported "true";
        yang:edit-supported "false";
        yang:delete-supported "false";
        type ciena-6500-enums:PSTfac_RTRV;
        description
          "Identify the primary State";
        config false;
      }
    }
    list facgrpmbr {
      yang:handler "tl1";
      yang:create-supported "true";
      yang:get-supported "true";
      yang:edit-supported "false";
      yang:delete-supported "true";
      key "facgrpmbr";
      config true;
      leaf facgrpmbr {
        mandatory true;
        description
          "AID in format FACGRPMBR-shelf-grpIx-mbrIx, FACGRPMBR-shelf-grpIx-ALL, FACGRPMBR-shelf-ALL, ALL";
        type ciena-6500-types:aid;
      }
      leaf mbraid {
        yang:create-supported "true";
        yang:get-supported "true";
        yang:delete-supported "false";
        type ciena-6500-types:aid;
        description
          "Facility AID of this member.";
        config true;
      }
      leaf mbrlatency {
        yang:create-supported "false";
        yang:get-supported "true";
        yang:delete-supported "false";
        type string {
          length "0..64";
        }
        description
          "Member latency.";
        config false;
      }
    }
    list vcp {
      yang:handler "tl1";
      yang:create-supported "true";
      yang:get-supported "true";
      yang:edit-supported "true";
      yang:delete-supported "true";
      key "vcp";
      config true;
      leaf vcp {
        mandatory true;
        description
          "AID in format VCP-shelf-vcpIdx, VCP-shelf-vcpIdx-dir, VCP-shelf-ALL, ALL";
        type ciena-6500-types:aid;
      }
      leaf vcp-type {
        yang:create-supported "true";
        yang:get-supported "true";
        yang:edit-supported "false";
        yang:delete-supported "false";
        type ciena-6500-enums:EnumVCPTYPE;
        mandatory true;
        description
          "This attribute indicates the type of ctps that can be connected to this VCP.";
        config true;
      }
      leaf label {
        yang:create-supported "true";
        yang:get-supported "true";
        yang:edit-supported "true";
        yang:delete-supported "false";
        type string {
          length "0..64";
        }
        description
          "This attribute is a customized description";
        config true;
      }
      leaf gep {
        yang:create-supported "true";
        yang:get-supported "true";
        yang:edit-supported "true";
        yang:delete-supported "false";
        type enumeration {
          enum YES;
          enum NO;
        }
        default "NO";
        description
          "Specifies whether this VCP end-point facility accepts Generict End Point (GEP) method.";
        config true;
      }
      leaf gep-name {
        yang:create-supported "true";
        yang:get-supported "true";
        yang:edit-supported "true";
        yang:delete-supported "false";
        type string {
          length "1..64";
        }
        description
          "Specifies the Generict End Point (GEP) name.";
        config true;
      }
      leaf vcp-dir {
        yang:create-supported "false";
        yang:get-supported "true";
        yang:edit-supported "false";
        yang:delete-supported "false";
        type ciena-6500-types:aid;
        description
          "VCP";
        config false;
      }
      leaf application-type {
        yang:create-supported "false";
        yang:get-supported "true";
        yang:edit-supported "false";
        yang:delete-supported "false";
        type enumeration {
          enum NONE;
          enum SNCP;
          enum UNI_SNCP;
        }
        description
          "The Application Type which identifies whether it is used in a protection scheme or not";
        config false;
      }
      leaf selector {
        yang:create-supported "false";
        yang:get-supported "true";
        yang:edit-supported "false";
        yang:delete-supported "false";
        type enumeration {
          enum FALSE {
            description
              "VCP is not acting as a selector";
          }
          enum TRUE {
            description
              "VCP is acting as a selector";
          }
        }
        description
          "Indicates if the VCP is acting as a selector or not";
        config false;
      }
      leaf size {
        yang:create-supported "false";
        yang:get-supported "true";
        yang:edit-supported "false";
        yang:delete-supported "false";
        type ciena-6500-types:INT {
          range "1..80";
        }
        description
          "Indicates the number of rate based timeslots that can be connected to the VCP. This attribute has a value of 1 when the VCP is not part of a GTP.";
        config false;
      }
      leaf fcc {
        yang:create-supported "false";
        yang:get-supported "true";
        yang:edit-supported "false";
        yang:delete-supported "false";
        type ciena-6500-types:aid;
        description
          "Reference to associated FCC, if applicable.";
        config false;
      }
      leaf usage-state {
        yang:create-supported "false";
        yang:get-supported "true";
        yang:edit-supported "false";
        yang:delete-supported "false";
        type enumeration {
          enum IDLE;
          enum BUSY;
          enum ACTIVE;
        }
        description
          "The type for Usage State.";
        config false;
      }
      leaf bit-rate {
        yang:create-supported "false";
        yang:get-supported "true";
        yang:edit-supported "false";
        yang:delete-supported "false";
        type string {
          length "0..64";
        }
        description
          "Define the bit rate of flex in bps.";
        config false;
      }
    }
  }
}
